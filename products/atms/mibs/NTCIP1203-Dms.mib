-- Copyright 1998-2024 by the American Association of State Highway and
-- Transportation Officials (AASHTO), the Institute of Transportation
-- Engineers (ITE), and the National Electrical Manufacturers Association
-- (NEMA). All intellectual property rights, including, but not limited to,
-- the rights of reproduction in whole or in part in any form, translation
-- into other languages and display are reserved by the copyright owners
-- under the laws of the United States of America, the Universal Copyright
-- Convention, the Berne Convention, and the International and Pan American
-- Copyright Conventions.
-- 
-- Joint NEMA, AASHTO, and ITE
-- NTCIP Management Information Base
-- DISTRIBUTION NOTICE
--
-- To the extent and in the limited event these materials are distributed by
-- AASHTO/ITE/NEMA in the form of a Management Information Base ("MIB"),
-- AASHTO/ITE/NEMA extends the following permissions:
--
-- You may make and distribute unlimited copies of this file, including
-- copies for commercial distribution, provided that:
--   (a) the copies are not edited from this official version and
--   (b) each copy contains this Notice
--
-- These materials are delivered "AS IS" without any warranties as to their
-- use or performance.
--
-- AASHTO/ITE/NEMA AND THEIR SUPPLIERS DO NOT WARRANT THE PERFORMANCE OR
-- RESULTS YOU MAY OBTAIN BY USING THESE MATERIALS. AASHTO/ITE/NEMA AND THEIR
-- SUPPLIERS MAKE NO WARRANTIES, EXPRESS OR IMPLIED, AS TO NONINFRINGEMENT OF
-- THIRD PARTY RIGHTS, MERCHANTABILITY, OR FITNESS FOR ANY PARTICULAR PURPOSE.
-- IN NO EVENT WILL AASHTO, ITE OR NEMA OR THEIR SUPPLIERS BE LIABLE TO YOU OR
-- ANY THIRD PARTY FOR ANY CLAIM OR FOR ANY CONSEQUENTIAL, INCIDENTAL OR
-- SPECIAL DAMAGES, INCLUDING ANY LOST PROFITS OR LOST SAVINGS, ARISING FROM
-- YOUR REPRODUCTION OR USE OF THESE MATERIALS, EVEN IF AN AASHTO, ITE, OR
-- NEMA REPRESENTATIVE HAS BEEN ADVISED OF THE POSSIBILITY OF SUCH DAMAGES.
-- Some states or jurisdictions do not allow the exclusion or limitation of
-- incidental, consequential or special damages, or the exclusion of implied
-- warranties, so the above limitations may not apply to you.
--
-- Use of these materials does not constitute an endorsement or affiliation by
-- or between AASHTO, ITE, or NEMA and you, your company, or your products and
-- services.
--
-- NTCIP is a trademark of AASHTO/ITE/NEMA.
--
-- 5.1	Object Definitions
NTCIP1203-Dms DEFINITIONS ::= BEGIN
IMPORTS
MODULE-IDENTITY, OBJECT-IDENTITY, OBJECT-TYPE, Integer32, Unsigned32, 
Counter32, IpAddress
                                               FROM SNMPv2-SMI
                                                 -- RFC 2578  
TEXTUAL-CONVENTION, DisplayString, StorageType, RowStatus
                                               FROM SNMPv2-TC
                                                 -- RFC 2579
OBJECT-GROUP
                                               FROM SNMPv2-CONF
                                                 -- RFC 2580
SnmpAdminString
                                               FROM SNMP-FRAMEWORK-MIB
                                                 -- RFC 3411
TransportAddressType, TransportAddress
                                               FROM TRANSPORT-ADDRESS-MIB
                                                 -- RFC 3419
ITSDirection, ITSInteger8, ITSLatitude84, ITSLongitude84,
ITSBitmap
                                               FROM ISO26048-1-Global-TC
fdSrsaTypeCode, fdSrsaPortIndex
                                               FROM ISO26048-1-Srsa
NtcipOwnerString, NtcipIntegerBitmap8, NtcipIntegerBitmap16, 
NtcipTwoColors, devices
                                               FROM NTCIP8004-Transportation;

dms MODULE-IDENTITY
  LAST-UPDATED "202504020500Z"
  ORGANIZATION "NTCIP DMS WG"
  CONTACT-INFO
   "name: NTCIP Coordinator
    email: ntcip@nema.org
    postal: National Electrical Manufacturers Association
            1300 North 17th Street, Suite 1752
            Rosslyn, Virginia 22209-3801"
  DESCRIPTION
  "<Definition> This MIB defines the structure of management information
    under the dms and adminDms nodes, which are used to manage dynamic
    message signs.
  <Object Identifier> 1.3.6.1.4.1.1206.4.2.3"

  REVISION "202504020500Z"
  DESCRIPTION
    "NTCIP 1203 v04 - Upgraded to SMIv2 format and incorporated objects from
      the ISO 20684 series into design."
  REVISION "201409300500Z"
  DESCRIPTION
    "NTCIP 1203 v03 - Addition of test procedures to the standard."
  REVISION "201011300500Z"
  DESCRIPTION
    "NTCIP 1203 v02 - Updated copyright, MIB distribution format, and 
      incorporated NTCIP 8004 format."
  REVISION "200107030500Z"
  DESCRIPTION
    "NTCIP 1203 v01A1 - Amendment 1. Corrections based on user experience."
  REVISION "199912010500Z"
  DESCRIPTION
    "NTCIP 1203 v01 - Adopted by AASHTO and ITE in 1998; editorial changes 
      for publication."
  REVISION "199703310500Z"
  DESCRIPTION
    "NEMA TS 3.6 - Initial version of MIB as approved by NEMA. "
  ::= { devices 6 }


MessageIDCode ::= TEXTUAL-CONVENTION
  DISPLAY-HINT  "1d.2dx2x"
  STATUS  current
  DESCRIPTION
  "The MessageIDCode consists of those parameters required to define a 
    message within a dmsMessageTable. It is defined as an OCTET STRING 
    containing the OER-encoding of the following ASN.1 structure:
      MessageIDCodeStructure ::= SEQUENCE 
      {
      messageMemoryType  INTEGER (0..255),
      messageNumber      INTEGER (0..65535),
      messageCRC         OCTET STRING (SIZE (2))
      }

    messageMemoryType (8 bits) shall indicate the dmsMessageMemoryType of 
    the desired message. The vaule of 'currentBuffer' (5) in this field 
    is discouraged unless the object type using this syntax indicates its 
    support and interpretation. For example, the dmsShortPowerRecoveryMessage 
    object type indicates that the value of 'currentBuffer' can be used to 
    allow a message that was running prior to a power loss to run after the 
    power loss without changing the contents of dmsShortPowerRecoveryMessage 
    every time the activateMessage is changed

    messageNumber (16 bits) shall indicate the dmsMessageNumber of the 
    desired message. In the case of a blank message, this field has an
    upper limit of 255; in the case of the scheduler or current buffer, 
    this field shall always be one (1).

    messageCRC (16 bits) shall indicate the dmsMessageCRC of the 
    desired message. In the case of a blank message, the scheduler, 
    or the current buffer, this value shall be 0x0000.

    For example, given the MULTI string '[jp3]TEST [fl]Flashing[/fl]',
    stored in volatile memory slot 5 with no physical beacons and no pixel
    service, the message ID Code is '04 00 05 95 F9', which would be 
    displayed as '4.5x95f', according to the 
    display hint. " 
  SYNTAX  OCTET STRING (SIZE(5))



MessageActivationCode ::= TEXTUAL-CONVENTION
  DISPLAY-HINT  "2dm1dp1d.2d#2x<1d.1d.1d.1d"
  STATUS  deprecated
  DESCRIPTION
  "The MessageActivationCode consists of those parameters required to 
    activate a message on a DMS. It is defined as an OCTET STRING 
    containing the OER-encoding of the following ASN.1 structure.

      MessageActivationCodeStructure ::= SEQUENCE 
      {
      duration            INTEGER (0..65535),
      activatePriority    INTEGER (0..255),
      messageMemoryType   INTEGER (0..255),
      messageNumber       INTEGER (0..65535),
      messageCRC          OCTET STRING (SIZE (2)),
      sourceAddress       OCTET STRING (SIZE (4))
      }

    duration (16 bits) shall indicate the maximum amount of time, in 
    minutes, the message may be displayed prior to activating the 
    dmsDefaultEndDurationMessage. dmsMessageTimeRemaining shall be set to 
    this value upon successful display of the indicated message. A 
    value of 65535 shall indicate an infinite duration. 

    activatePriority (8 bits) shall indicate the Activation Priority of 
    the message. If this value is greater than or equal to the
    dmsMessageRunTimePriority of the currently displayed message, the new 
    message shall be displayed unless errors are detected. 

    messageMemoryType (8 bits) shall indicate the dmsMessageMemoryType of 
    the desired message. The vaule of 'currentBuffer' (5) in this field 
    shall be considered an error.

    messageNumber (16 bits) shall indicate the dmsMessageNumber of the 
    desired message. In the case of a blank message, this field has an
    upper limit of 255; in the case of the scheduler, this field shall 
    always be one (1).

    messageCRC (16 bits) shall indicate the dmsMessageCRC of the 
    desired message.

    sourceAddress (32 bits) shall indicate the 4-byte IP address of the 
    device which requested the activation. 

    For example, given the MULTI string '[jp3]TEST [fl]Flashing[/fl]',
    stored in volatile memory slot 5 with no physical beacons and no pixel
    service, the message ID Code is '04 00 05 95 F9'. If this message
    is to be displayed for 267 minutes with activation priority 55 from
    IP address 103.8.9.10, the message Activation Code is
    '01 0B 37 04 00 05 95 F9 67 08 09 0A', which would be displayed as 
    '267m55p4.5x95f9<103.8.9.10', according to the display hint.


    The dmsActivateMsgError object shall be used to indicate the success 
    or failure of activating any message requested by an object with a 
    SYNTAX of MessageActivationCode.
    
    This textual convention was deprecated in NTCIP 1203 v04 and superseded 
    with MessageActivationCodeV4, which removes the source address since this 
    can now be determined by the lower layer protocols (i.e., the NTCIP 2201 
    profile is no longer allowed and the migration allows IPv6)."
  SYNTAX  OCTET STRING (SIZE(12))

MessageActivationCodeV4 ::= TEXTUAL-CONVENTION
  DISPLAY-HINT  "2dm1dp1d.2d#2x"
  STATUS  current
  DESCRIPTION
  "The MessageActivationCodeV4 consists of those parameters required to 
    activate a message on a DMS. It is defined as an OCTET STRING 
    containing the OER-encoding of the following ASN.1 structure.

      MessageActivationCodeStructureV4 ::= SEQUENCE 
      {
      duration            INTEGER (0..65535),
      activatePriority    INTEGER (0..255),
      messageMemoryType   INTEGER (0..255),
      messageNumber       INTEGER (0..65535),
      messageCRC          OCTET STRING (SIZE (2))
      }

    duration (16 bits) shall indicate the maximum amount of time, in 
    minutes, the message may be displayed prior to activating the 
    dmsDefaultEndDurationMessage. dmsMessageTimeRemaining shall be set to 
    this value upon successful display of the indicated message. A 
    value of 65535 shall indicate an infinite duration. 

    activatePriority (8 bits) shall indicate the Activation Priority of 
    the message. If this value is greater than or equal to the
    dmsMessageRunTimePriority of the currently displayed message, the new 
    message shall be displayed unless errors are detected. 

    messageMemoryType (8 bits) shall indicate the dmsMessageMemoryType of 
    the desired message. The vaule of 'currentBuffer' (5) in this field 
    shall be considered an error.

    messageNumber (16 bits) shall indicate the dmsMessageNumber of the 
    desired message. In the case of a blank message, this field has an
    upper limit of 255; in the case of the scheduler, this field shall 
    always be one (1).

    messageCRC (16 bits) shall indicate the dmsMessageCRC of the 
    desired message.

    The source address, which was previously included within the
    MessageActivationCode structure used in NTCIP 1203 v01 through v03, is
    no longer contained within this structure. Instead, the device shall 
    determine the source address and security name from the lower layers 
    of the request containing this structure. 

    For example, given the MULTI string '[jp3]TEST [fl]Flashing[/fl]',
    stored in volatile memory slot 5 with no physical beacons and no pixel
    service, the message ID Code is '04 00 05 95 F9'. If this message
    is to be displayed for 267 minutes with activation priority 55 from
    UDP/IPv4 address of 103.8.9.10 on port 161 and a securityName of 'TMC 
    operator', the activation code is '01 0B 37 04 00 05 95 F9', which would 
    be displayed as '267m55p4.5x95f9', according to the display hint. Upon 
    successful display, the field device would update
    dmsMsgRequesterAddressType to be udpIpv4 (1), dmsMsgRequesterAddress to
    be '67 08 09 0A 00 A1' and dmsMsgRequesterSecurityName to 'TMC operator'.


    The dmsActivateMsgError object shall be used to indicate the success 
    or failure of activating any message requested by an object with a 
    SYNTAX of MessageActivationCodeV4."
  SYNTAX  OCTET STRING (SIZE(8))

MultiString ::= TEXTUAL-CONVENTION
DISPLAY-HINT  "2048t"
STATUS        current 
DESCRIPTION  
"A string of zero (0) to dmsMaxMultiStringLength octets representing a 
message for display on the sign face:
- written in MULTI-language as defined in Section 6, 
- encoded as defined by defaultCharacterSet, and
- subranged by the restrictions defined by 
  - the dmsMaxMultiStringLength,
  - the dmsSupportedMultiTagsV5, and 
  - the values of defaultCharacterSet supported, and
  - the level of support for utf8Style encoding supported. 
The value is not allowed to have any null character."
SYNTAX  OCTET STRING

DmsColorScheme ::= TEXTUAL-CONVENTION
STATUS        current
DESCRIPTION
"<Definition> An indication of a color scheme. The values are defined as:
  monochrome1bit (1): Only two states are available: on (1) and off (0). 
  monochrome8bit (2): This color palette supports up to 256 shades ranging 
      from 0 (off) to 255 (full intensity). Values between zero and 255 are 
      scaled to the nearest intensity level supported. Implementations are 
      not required to support true 8-bit (256 shade) capabilities.
  colorClassic (3): Color is indicated using the DMSClassicColor textual 
      convention. 
  color24bit (4): The color is defined by three octet, one each for red, 
      green, and blue. Each color value for each octet ranges from 0 (off) to 
      255 (full intensity). The combination of the red, green, and blue 
      colors supports 16,777,216 colors. Values between zero and 255 are 
      scaled to the nearest intensity level supported. Implementations are 
      not required to support true 8-bit (256 shade) capability and can 
      support a small subrange. For example, a physical beacon might only 
support red 
      or amber; the 24 bit value is rounded to the closest match that the 
      equipment suports. It is the responsibility of the hardware 
      specification to identify the hardware capabilities."
SYNTAX      INTEGER {
                 monochrome1bit (1),
                 monochrome8bit (2),
                 colorClassic (3),
                 color24bit(4)} 


DmsClassicColor ::= TEXTUAL-CONVENTION
STATUS        current
DESCRIPTION
"An enumerated color code used by implementations that use the 'colorClassic' 
value of dmsColorScheme. Each color code is to be mapped to a specific 
similar color supported by the sign. If a color code is not mapped to a 
supported color (e.g., the sign does not support an enumerated color), the 
associated enumerated value shall not be supported by the sign. "
SYNTAX    INTEGER { black (0),
                    red (1),
                    yellow (2),
                    green(3),
                    cyan (4),
                    blue (5),
                    magenta (6),
                    white (7),
                    orange (8),
                    amber (9) } 

DmsColor ::= TEXTUAL-CONVENTION
DISPLAY-HINT  "1dR1dG1dB"
STATUS        current
DESCRIPTION
"A color code interpreted based on the value of the dmsColorScheme object, 
which is a read-only object that should not change in an implementation. 

If dmsColorScheme is equal to 'monochrome1bit', the DmsColor shall be a one-
octet value of either off (0x00) or on (0x01). The actual color shall be 
indicated by the monochromeColor object.

If dmsColorScheme is equal to 'monochrome8bit', the DmsColor shall be a one-
octet value representing a value as defined by DmsClassicColor intensity of 
the single color on a scale of 0-255. The actual color shall be indicated by 
the monochromeColor object.

If dmsColorScheme is equal to 'colorClassic', the DmsColor shall be a one-
octet value representing a value as defined by DmsClassicColor. 

If dmsColorScheme is equal to 'color24bit', the DmsColor shall be a three-
octet RGB color scheme value. The first octet shall represent the intensity 
of red, the second octet shall represent the intensity of green, and the 
third octet shall represent the intensity of blue, each on a scale of 0-255."
  SYNTAX  OCTET STRING (SIZE(1 | 3))

-- 5.2	Sign Configuration and Capability Objects 
dmsSignCfg  OBJECT-IDENTITY 
STATUS  current
DESCRIPTION
"This node is an identifier used to group all objects for DMS sign 
configurations that are common to all DMS devices. 
<Object Identifier> 1.3.6.1.4.1.1206.4.2.3.1"
::= { dms 1 }


-- 5.2.1	Sign Access Parameter 
dmsSignAccess  OBJECT-TYPE 
SYNTAX      NtcipIntegerBitmap8 
MAX-ACCESS  read-only 
STATUS      current 
DESCRIPTION  
"<Definition> Indicates the access method to the sign. Methods that are 
defined are:
<Format>
  Bit 0- Other 
  Bit 1- Walk-in access
  Bit 2- Rear access
  Bit 3- Front access
If a bit is set to one (1), then the associated feature exists; if the bit is 
set to zero (0), then the associated feature does not exist. 
<Parameter Type> Status
<Object Identifier> 1.3.6.1.4.1.1206.4.2.3.1.1" 
::= { dmsSignCfg 1 }

-- 5.2.2	Sign Type Parameter 
dmsSignType  OBJECT-TYPE
SYNTAX      INTEGER{
                 other (1),
                 bos (2),
                 cms (3),
                 vmsChar (4),
                 vmsLine (5),
                 vmsFull (6),
                 portableOther (129),
                 portableBOS (130),
                 portableCMS (131),
                 portableVMSChar (132),
                 portableVMSLine (133),
                 portableVMSFull (134)} 
MAX-ACCESS  read-only 
STATUS      current 
DESCRIPTION  
"<Definition> Indicates the type of sign. 
<Format>The descriptions are:
  other:  Device not specified through any other definition, refer to
     device manual,
  bos: Device is a Blank-Out Sign,
  cms : Device is a Changeable Message Sign,
  vmsChar : Device is a Variable Message Sign with character matrix 
     setup,
  vmsLine :  Device is a Variable Message Sign with line matrix setup,
  vmsFull: Device is a Variable Message Sign with full matrix setup.
  Same is true for all portable signs. 
<Parameter Type> Status
<Object Identifier> 1.3.6.1.4.1.1206.4.2.3.1.2"
::= { dmsSignCfg 2 }

-- 5.2.3	Sign Height Parameter 
dmsSignHeight  OBJECT-TYPE 
SYNTAX      Integer32 (0..65535) 
UNITS       "millimeters"
MAX-ACCESS  read-only 
STATUS      current 
DESCRIPTION  
"<Definition> Indicates the sign height in millimeters including the border 
(dmsVerticalBorder). 
<Parameter Type> Status<Object Identifier> 1.3.6.1.4.1.1206.4.2.3.1.3" 
::= { dmsSignCfg 3 }

-- 5.2.4	Sign Width Parameter 
dmsSignWidth  OBJECT-TYPE 
SYNTAX      Integer32 (0..65535) 
UNITS       "millimeters"
MAX-ACCESS  read-only 
STATUS      current 
DESCRIPTION  
"<Definition> Indicates the sign width in millimeters including the border 
(dmsHorizontalBorder). 
<Parameter Type> Status
<Object Identifier> 1.3.6.1.4.1.1206.4.2.3.1.4" 
::= { dmsSignCfg 4 }

-- 5.2.5	Horizontal Border Parameter 
dmsHorizontalBorder  OBJECT-TYPE 
SYNTAX      Integer32 (0..65535) 
UNITS       "millimeters"
MAX-ACCESS  read-only 
STATUS      current  
DESCRIPTION  
"<Definition> Indicates the minimum border distance, in millimeters, that 
exists on the left and right sides of the sign. 
<Parameter Type> Status
<Object Identifier> 1.3.6.1.4.1.1206.4.2.3.1.5" 
::= { dmsSignCfg 5 }

-- 5.2.6	Vertical Border Parameter 
dmsVerticalBorder  OBJECT-TYPE 
SYNTAX      Integer32 (0..65535) 
UNITS       "millimeters"
MAX-ACCESS  read-only 
STATUS      current  
DESCRIPTION  
"<Definition> Indicates the minimum border distance, in millimeters, that 
exists on the top and bottom of the sign. 
<Parameter Type> Status
<Object Identifier> 1.3.6.1.4.1.1206.4.2.3.1.6" 
::= { dmsSignCfg 6 }

-- 5.2.7	Legend Parameter 
dmsLegend  OBJECT-TYPE 
SYNTAX      INTEGER {
                 other (1), -- deprecated
                 noLegend (2),
                 legendExists (3)} 
MAX-ACCESS  read-only 
STATUS      current 
DESCRIPTION  
"<Definition> Indicates if a Legend is shown on the sign. 
<Format> In v02, the enumerated value of 'other' was retired to improve 
interoperability and since this is a logical Boolean value with no real other 
alternative possible.
<Informative> The value of other was deprecated in v02 to improve 
interoperability.
<Parameter Type> Status
<Object Identifier> 1.3.6.1.4.1.1206.4.2.3.1.7" 
::= { dmsSignCfg 7 }

-- 5.2.8	Beacon Type Parameter 
dmsBeaconType  OBJECT-TYPE 
SYNTAX      INTEGER {
                 other (1),
                 none (2),
                 oneBeacon (3),
                 twoBeaconSyncFlash (4),
                 twoBeaconsOppFlash (5),
                 fourBeaconSyncFlash (6),
                 fourBeaconAltRowFlash (7),
                 fourBeaconAltColumnFlash (8),
                 fourBeaconAltDiagonalFlash (9),
                 fourBeaconNoSyncFlash (10),
                 oneBeaconStrobe (11),
                 twoBeaconStrobe (12),
                 fourBeaconStrobe (13)} 
MAX-ACCESS  read-only 
STATUS      deprecated  
DESCRIPTION  
"<Definition> Indicates the configuration of the type, numbers and flashing 
patterns of beacons on a sign. 
<Format> The definitions are: 
  other: other types, numbers and patterns of beacons attached to the 
     sign display.
  none: no beacons attached to the sign display
  oneBeacon: one flashing beacon
  twoBeaconSyncFlash: two beacons, synchronized flashing 
  twoBeaconsOppFlash: two beacons, opposing flashing
  fourBeaconSyncFlash:  four beacons, synchronized flashing
  fourBeaconAltRowFlash: four beacons, alternate row flashing
  fourBeaconAltColumnFlash: four beacons, alternate column flashing
  fourBeaconAltDiagonalFlash: four beacons, alternate diagonal 
     flashing
  fourBeaconNoSyncFlash: four beacons, no synchronized flashing
  oneBeaconStrobe: one beacon, strobe light
  twoBeaconStrobe: two beacons, strobe light
  fourBeaconStrobe: four beacons, strobe light 
<Superseded by> dmsBeaconTable and dmsBeaconPlanTable
<Informative> This object was deprecated in v04 in favor of a more robust 
beacon design.
<Parameter Type> Status
<Object Identifier> 1.3.6.1.4.1.1206.4.2.3.1.8" 
::= { dmsSignCfg 8 }

-- 5.2.9	Sign Technology Parameter 
dmsSignTechnology  OBJECT-TYPE 
SYNTAX      NtcipIntegerBitmap16  
MAX-ACCESS  read-only 
STATUS      current  
DESCRIPTION  
"<Definition> Indicates the utilized technology in a bitmap format  (Hybrids 
will have to set the bits for all technologies that the sign utilizes).
<Format>
  Bit 0- Other,
  Bit 1- LED,
  Bit 2- Flip Disk,
  Bit 3- Fiber Optics,
  Bit 4- Shuttered,
  Bit 5- Bulb,
  Bit 6- Drum
  Bits 7-15- Reserved

If a bit is set to one (1), then the associated feature exists; if the 
bit is set to zero (0), then the associated feature does not exist.
<Informative> The value of LED would be encoded as an integer value of 2. 
<Parameter Type> Status
<Object Identifier> 1.3.6.1.4.1.1206.4.2.3.1.9" 
::= { dmsSignCfg 9 }

-- 5.2.10	Sign Display Latitude
dmsDisplayLatitude  OBJECT-TYPE 
SYNTAX      ITSLatitude84
UNITS       "microdegrees" 
MAX-ACCESS  read-only 
STATUS      current  
DESCRIPTION  
"<Definition> Indicates the latitude of the sign display as determined by the 
sum of fdConfiguredLatitude (which identifies the location of the GNSS 
antenna or similar reference point) and dmsDisplayOffsetLatitude. 
<Parameter Type> Status
<Object Identifier> 1.3.6.1.4.1.1206.4.2.3.1.10"
::= { dmsSignCfg 10 }

-- 5.2.11	Sign Display Longitude
dmsDisplayLongitude  OBJECT-TYPE 
SYNTAX      ITSLongitude84
UNITS       "microdegrees" 
MAX-ACCESS  read-only 
STATUS      current  
DESCRIPTION  
"<Definition> Indicates the longitude of the sign display as determined by 
the sum of fdConfiguredLongitude (which identifies the location of the GNSS 
antenna or similar reference point) and dmsDisplayOffsetLongitude.
<Parameter Type> Status
<Object Identifier> 1.3.6.1.4.1.1206.4.2.3.1.11"
::= { dmsSignCfg 11 }

-- 5.2.12	Sign Display Direction
dmsDisplayDirection  OBJECT-TYPE 
SYNTAX      ITSDirection
UNITS       "degrees" 
MAX-ACCESS  read-write 
STATUS      current  
DESCRIPTION  
"<Definition> Indicates the direction that the sign faces. A value of 0 
indicates a northward facing sign providing messages for southbound traffic. 
A value of 90 indictes an eastward facing sign providing messages for 
westbound traffic.
<Parameter Type> Configuration
<Object Identifier> 1.3.6.1.4.1.1206.4.2.3.1.12"
::= { dmsSignCfg 12 }

-- 5.2.13	Sign Display Offset Latitude
dmsDisplayOffsetLatitude  OBJECT-TYPE 
SYNTAX      ITSLatitude84
UNITS       " microdegrees" 
MAX-ACCESS  read-write 
STATUS      current  
DESCRIPTION  
"<Definition> Indicates the difference in latitude between the GNSS antenna 
location (or other point upon which fdConfiguredLongitude is based) and the 
center of the sign display.
<Parameter Type> Configuration
<Object Identifier> 1.3.6.1.4.1.1206.4.2.3.1.13"
::= { dmsSignCfg 13 }

-- 5.2.14	Sign Display Offset Longitude
dmsDisplayOffsetLongitude  OBJECT-TYPE 
SYNTAX      ITSLongitude84
UNITS       "microdegrees" 
MAX-ACCESS  read-write 
STATUS  current
DESCRIPTION
"<Definition> Indicates the difference in longitude between the GNSS antenna 
location (or other point upon which fdConfiguredLongitude is based) and the 
center of the sign display.
<Parameter Type> Configuration
<Object Identifier> 1.3.6.1.4.1.1206.4.2.3.1.14"
::= { dmsSignCfg 14 }

-- 5.2.15	Beacon Operation Objects
dmsBeacon  OBJECT-IDENTITY 
STATUS  current
DESCRIPTION
"<Definition> A node used to provide information about physical beacons 
associated with the sign.
<Object Identifier> 1.3.6.1.4.1.1206.4.2.3.1.15"
::= { dmsSignCfg 15 }

-- 5.2.15.1	Number of Beacons
dmsBeaconCount  OBJECT-TYPE 
SYNTAX      Integer32 (0..255)
UNITS       "beacons" 
MAX-ACCESS  read-only 
STATUS      current  
DESCRIPTION  
"<Definition> Indicates the number of physical beacons managed by the DMS.
<Parameter Type> Status
<Object Identifier> 1.3.6.1.4.1.1206.4.2.3.1.15.1"
::= { dmsBeacon 1 }

-- 5.2.15.2	Maximum Beacon Plans
dmsBeaconMaxPlans  OBJECT-TYPE 
SYNTAX      Integer32 (0..255)
UNITS       "beacon plans" 
MAX-ACCESS  read-only 
STATUS      current  
DESCRIPTION  
"<Definition> Indicates the maximum number of beacon plans that can be 
managed by the DMS.
<Parameter Type> Status
<Object Identifier> 1.3.6.1.4.1.1206.4.2.3.1.15.2"
::= { dmsBeacon 2 }

-- 5.2.15.3	Beacon Table
dmsBeaconTable  OBJECT-TYPE 
SYNTAX      SEQUENCE OF DmsBeaconEntry
MAX-ACCESS  not-accessible  
STATUS      current  
DESCRIPTION  
"<Definition> A table containing the information needed to identify the 
physical beacons associated with the DMS.
<Table Type> static
<Object Identifier> 1.3.6.1.4.1.1206.4.2.3.1.15.3"
::= { dmsBeacon 3 }

dmsBeaconEntry  OBJECT-TYPE 
SYNTAX      DmsBeaconEntry
MAX-ACCESS  not-accessible  
STATUS      current  
DESCRIPTION  
"<Definition> A row within the dmsBeaconTable, which contains the information 
needed to identify the physical beacons associated with the DMS.
<Table Type> static
<Object Identifier> 1.3.6.1.4.1.1206.4.2.3.1.15.3.1"
INDEX {dmsBeaconIndex}
::= { dmsBeaconTable 1 }

DmsBeaconEntry ::= SEQUENCE {
      dmsBeaconIndex            Integer32,
      dmsBeaconXLocation        Integer32,
      dmsBeaconYLocation        Integer32,
      dmsBeaconWidth            Integer32,
      dmsBeaconHeight           Integer32,
      dmsBeaconColorScheme      DmsColorScheme,
      dmsBeaconFlashResolution  Integer32 }

-- 5.2.15.3.1	Beacon Index Parameter 
dmsBeaconIndex  OBJECT-TYPE 
SYNTAX      Integer32 (1..255) 
MAX-ACCESS  not-accessible 
STATUS      current  
DESCRIPTION  
"<Definition> Sequential index of the beacon starting with beacon 1.
<Object Identifier> 1.3.6.1.4.1.1206.4.2.3.1.15.3.1.1"
::= { dmsBeaconEntry 1 }

-- 5.2.15.3.2	Beacon X Location Parameter 
dmsBeaconXLocation  OBJECT-TYPE 
SYNTAX      Integer32
UNITS       "millimeters" 
MAX-ACCESS  read-only 
STATUS      current  
DESCRIPTION  
"<Definition> The horizontal distance from the left-most point of the sign 
border to the center of the beacon. A positive value shall indicate a 
location to the right; a negative value shall indicate a location to the 
left.
<Parameter Type> Status
<Object Identifier> 1.3.6.1.4.1.1206.4.2.3.1.15.3.1.2"
::= { dmsBeaconEntry 2 }

-- 5.2.15.3.3	Beacon Y Location Parameter 
dmsBeaconYLocation  OBJECT-TYPE 
SYNTAX      Integer32
UNITS       "millimeters" 
MAX-ACCESS  read-only 
STATUS      current  
DESCRIPTION  
"<Definition> The vertical distance from the lowest point of the sign border 
to the center of the beacon. A positive value shall indicate a location above 
the lowest point of the border; a negative value shall indicate a location 
below.
<Parameter Type> Status
<Object Identifier> 1.3.6.1.4.1.1206.4.2.3.1.15.3.1.3"
::= { dmsBeaconEntry 3 }

-- 5.2.15.3.4	Beacon Width Parameter 
dmsBeaconWidth  OBJECT-TYPE 
SYNTAX      Integer32
UNITS       "millimeters" 
MAX-ACCESS  read-only 
STATUS      current  
DESCRIPTION  
"<Definition> The width of the illumination area of the beacon. Circular and 
square beacons shall have identical values for dmsBeaconWidth and 
dmsBeaconHeight.
<Parameter Type> Status
<Object Identifier> 1.3.6.1.4.1.1206.4.2.3.1.15.3.1.4"
::= { dmsBeaconEntry 4 }

-- 5.2.15.3.5	Beacon Height Parameter 
dmsBeaconHeight  OBJECT-TYPE 
SYNTAX      Integer32
UNITS       "millimeters" 
MAX-ACCESS  read-only 
STATUS      current  
DESCRIPTION  
"<Definition> The height of the illumination area of the beacon. Circular and 
square beacons shall have identical values for dmsBeaconWidth and 
dmsBeaconHeight.
<Parameter Type> Status
<Object Identifier> 1.3.6.1.4.1.1206.4.2.3.1.15.3.1.5"
::= { dmsBeaconEntry 5 }

-- 5.2.15.3.6	Beacon Color Scheme Parameter 
dmsBeaconColorScheme  OBJECT-TYPE 
SYNTAX      DmsColorScheme
MAX-ACCESS  read-only 
STATUS      current  
DESCRIPTION  
"<Definition> Indicates the color scheme supported by the beacon.
<Parameter Type> Status
<Object Identifier> 1.3.6.1.4.1.1206.4.2.3.1.15.3.1.6"
::= { dmsBeaconEntry 6 }

-- 5.2.15.3.7	Beacon Flash Resolution Parameter 
dmsBeaconFlashResolution  OBJECT-TYPE 
SYNTAX      Integer32
UNITS       "milliseconds"
MAX-ACCESS  read-only 
STATUS      current  
DESCRIPTION  
"<Definition> Indicates the resolution of the flash duration control. For 
example, a value of 500 would indicate that the beacon flash parameters can 
control the flash (on) period and flash cycle in steps of 500 ms (i.e., 0.5 
s).
<Parameter Type> Status
<Object Identifier> 1.3.6.1.4.1.1206.4.2.3.1.15.3.1.7"
::= { dmsBeaconEntry 7 }

-- 5.2.15.4	Beacon Plan Table
dmsBeaconPlanTable  OBJECT-TYPE 
SYNTAX      SEQUENCE OF DmsBeaconPlanEntry
MAX-ACCESS  not-accessible  
STATUS      current  
DESCRIPTION  
"<Definition> A table containing the operational plan information used to 
control a set of physical beacons associated with the DMS.
<Table Type> dynamic
<Object Identifier> 1.3.6.1.4.1.1206.4.2.3.1.15.4"
::= { dmsBeacon 4 }

dmsBeaconPlanEntry  OBJECT-TYPE 
SYNTAX      DmsBeaconPlanEntry
MAX-ACCESS  not-accessible  
STATUS      current  
DESCRIPTION  
"<Definition> A row within the dmsBeaconPlanTable, which contains the 
operational plan information used to control a set of physical beacons 
associated with the DMS.
<Table Type> dynamic
<Object Identifier> 1.3.6.1.4.1.1206.4.2.3.1.15.4.1"
INDEX {dmsBeaconPlanIndex}
::= { dmsBeaconPlanTable 1 }

DmsBeaconPlanEntry ::= SEQUENCE {
      dmsBeaconPlanIndex        Integer32,
      dmsBeaconPlanDescr        SnmpAdminString,
      dmsBeaconPlanCycle        Unsigned32,
      dmsBeaconPlanStorageType  StorageType,
      dmsBeaconPlanRowStatus    RowStatus }

-- 5.2.15.4.1	Beacon Plan Index Parameter 
dmsBeaconPlanIndex  OBJECT-TYPE 
SYNTAX      Integer32 (1..255) 
MAX-ACCESS  not-accessible 
STATUS      current  
DESCRIPTION  
"<Definition> Index of the beacon plan.
<Object Identifier> 1.3.6.1.4.1.1206.4.2.3.1.15.4.1.1"
::= { dmsBeaconPlanEntry 1 }

-- 5.2.15.4.2	Beacon Plan Description Parameter 
dmsBeaconPlanDescr  OBJECT-TYPE 
SYNTAX      SnmpAdminString  
MAX-ACCESS  read-create 
STATUS      current  
DESCRIPTION  
"<Definition> Textual description of the beacon plan.
<Parameter Type> Configuration
<Object Identifier> 1.3.6.1.4.1.1206.4.2.3.1.15.4.1.2"
::= { dmsBeaconPlanEntry 2 }

-- 5.2.15.4.3	Beacon Plan Cycle Parameter 
dmsBeaconPlanCycle  OBJECT-TYPE 
SYNTAX      Unsigned32 (0..60000)
UNITS       "milliseconds" 
MAX-ACCESS  read-create 
STATUS      current  
DESCRIPTION  
"<Definition> The duration required to complete one entire flash cycle. The 
flash cycle zero-point shall be based on the previously occuring local 
midnight, if the local clock feature is supported, and midnight UTC if not. 
The plan cycle shall be a multiple of dmsBeaconFlashResolution.
<Infomative> Longer flash cycles allow lights to flash in order across 
multiple beacons. Coordinating the flash cycles at local midnight allows 
coordinated flashing across multiple devices. It is recommended that the 
cycle length is a denominator of 86,400,000 to prevent cycle anomalies at 
midnight on a regular basis. Ideally, the cycle length should be a 
denominator of 1,000 to prevent anomailes under nearly all conditions (e.g., 
leap seconds).   
<Parameter Type> Configuration
<Object Identifier> 1.3.6.1.4.1.1206.4.2.3.1.15.4.1.3"
DEFVAL { 1000 }
::= { dmsBeaconPlanEntry 3 }

-- 5.2.15.4.4	Beacon Storage Type Parameter 
dmsBeaconPlanStorageType  OBJECT-TYPE 
SYNTAX      StorageType  
MAX-ACCESS  read-create 
STATUS      current  
DESCRIPTION  
"<Definition> This object defines whether this beacon plan and all of its 
component details are kept in volatile storage and lost upon reboot or if 
this row is stored in non-volatile or permanent storage. Conceptual rows 
having the value 'permanent' shall allow write access to 
dmsBeaconPlanRowStatus (i.e., to change to either 'active' or 
'notInService'). 
<Parameter Type> Configuration
<Object Identifier> 1.3.6.1.4.1.1206.4.2.3.1.15.4.1.4"
::= { dmsBeaconPlanEntry 4 }

-- 5.2.15.4.5	Beacon Row Status Parameter 
dmsBeaconPlanRowStatus  OBJECT-TYPE 
SYNTAX      RowStatus  
MAX-ACCESS  read-create 
STATUS      current  
DESCRIPTION  
"<Definition> The status of this beacon plan. A 'destroy' command for this 
object shall also destroy all dmsBeaconPlanDetailEntries associated with this 
plan.
 
Only this object can be modified when the value of this object is 'active'. 
An attempt to change the state of this object while the beacon plan is in use 
by the current message shall result in a 'inconsistentValue' error.

This object shall only have a value of 'active' when its dmsBeaconPlanCycle 
is divisible by all associated dmsBeaconPlanDetailCycle objects. 
Implementations shall support both createAndGo and createAndWait.
<Parameter Type> Configuration
<Object Identifier> 1.3.6.1.4.1.1206.4.2.3.1.15.4.1.5"
::= { dmsBeaconPlanEntry 5 }

-- 5.2.15.5	Beacon Plan Detail Table
dmsBeaconPlanDetailTable  OBJECT-TYPE 
SYNTAX      SEQUENCE OF DmsBeaconPlanDetailEntry
MAX-ACCESS  not-accessible  
STATUS      current  
DESCRIPTION  
"<Definition> A table containing the operational details used to control a 
single physical beacon as a part of a beacon plan.
<Table Type> dynamic
<Object Identifier> 1.3.6.1.4.1.1206.4.2.3.1.15.5"
::= { dmsBeacon 5 }

dmsBeaconPlanDetailEntry  OBJECT-TYPE 
SYNTAX      DmsBeaconPlanDetailEntry
MAX-ACCESS  not-accessible  
STATUS      current  
DESCRIPTION  
"<Definition> A row within the dmsBeaconPlanDetailTable, which contains the 
operational details used to control a single physical beacon as a part of a 
beacon plan.
<Table Type> dynamic
<Object Identifier> 1.3.6.1.4.1.1206.4.2.3.1.15.5.1"
INDEX {dmsBeaconPlanIndex, dmsBeaconIndex }
::= { dmsBeaconPlanDetailTable 1 }

DmsBeaconPlanDetailEntry ::= SEQUENCE {
      dmsBeaconPlanDetailCycle   Unsigned32,
      dmsBeaconPlanDetailOffset  Unsigned32,
      dmsBeaconPlanDetailFlash   Unsigned32,
      dmsBeaconPlanDetailColor   DmsColor }

-- 5.2.15.5.1	Beacon Plan Detail Cycle Parameter 
dmsBeaconPlanDetailCycle  OBJECT-TYPE 
SYNTAX      Unsigned32 (0..60000)
UNITS       "milliseconds" 
MAX-ACCESS  read-create  
STATUS      current  
DESCRIPTION  
"<Definition> The duration required to complete one entire flash cycle for 
the specific beacon. The flash cycle zero-point shall be based on the 
previously occuring local midnight, if the local clock feature is supported, 
and midnight UTC if not. The value of dmsBeaconPlanCycle shall be divisible 
by this value prior to dmsBeaconPlanRowStatus becoming active. The flash 
cycle shall be a multiple of dmsBeaconFlashResolution. 
<Infomative> By setting the dmsBeaconPlanDetailCycle to be half of the 
dmsBeaconPlanCycle, a beacon can flash twice during one plan cycle.
<Parameter Type> Configuration
<Object Identifier> 1.3.6.1.4.1.1206.4.2.3.1.15.5.1.1"
DEFVAL { 1000 }
::= { dmsBeaconPlanDetailEntry 1 }

-- 5.2.15.5.2	Beacon Plan Detail Offset Parameter 
dmsBeaconPlanDetailOffset  OBJECT-TYPE 
SYNTAX      Unsigned32 (0..60000) 
UNITS       "milliseconds" 
MAX-ACCESS  read-create  
STATUS      current  
DESCRIPTION  
"<Definition> The point within the dmsBeaconPlanDetailCycle period at which 
the beacon illuminates and begins its flash period. The offset shall be less 
than dmsBeaconPlanDetailCycle and and a multiple of dmsBeaconFlashResolution 
prior to dmsBeaconPlanRowStatus becoming active.    
<Infomative> An alternate flash pattern can be configured by setting one 
beacon to have a zero offset and a second beacon to have a offset that is 
equal to one half of the cycle length used for the two beacons. 
<Parameter Type> Configuration
<Object Identifier> 1.3.6.1.4.1.1206.4.2.3.1.15.5.1.2"
DEFVAL { 0 }
::= { dmsBeaconPlanDetailEntry 2 }

-- 5.2.15.5.3	Beacon Plan Detail Flash Parameter 
dmsBeaconPlanDetailFlash  OBJECT-TYPE 
SYNTAX      Unsigned32 (0..60000) 
UNITS       "milliseconds" 
MAX-ACCESS  read-create  
STATUS      current  
DESCRIPTION  
"<Definition> The duration that the beacon will be illuminated when it 
flashes (i.e., the 'flash period'). This value shall be a multiple of 
dmsBeaconFlashResolution.
<Parameter Type> Configuration
<Object Identifier> 1.3.6.1.4.1.1206.4.2.3.1.15.5.1.3"
DEFVAL { 500 }
::= { dmsBeaconPlanDetailEntry 3 }

-- 5.2.15.5.4	Beacon Plan Detail Color Parameter 
dmsBeaconPlanDetailColor  OBJECT-TYPE 
SYNTAX      DmsColor 
MAX-ACCESS  read-create  
STATUS      current  
DESCRIPTION  
"<Definition> The color of the beacon flash. 

If the dmsBeaconColorScheme is monochrome1bit, the value can only be 1. If 
the dmsBeaconColorScheme is monochrome8bit, the DMS shall accept any single 
octet value and will transpose the value to the closest value that the beacon 
supports (i.e., the beacon does not have to support all 255 levels of 
illumination). If dmsBeaconColorScheme is colorClassic, the DMS shall only 
accept values supported by the DMS. If the value is color24bit, the DMS shall 
accept any three-octet value and will transpose the value to the closest 
value that the beacon supports (i.e., the beacon does not have to support all 
possible color combinations).
<Parameter Type> Configuration
<Object Identifier> 1.3.6.1.4.1.1206.4.2.3.1.15.5.1.4"
::= { dmsBeaconPlanDetailEntry 4 }

-- 5.3	VMS Configuration Objects 
vmsCfg  OBJECT-IDENTITY
STATUS  current
DESCRIPTION
"This subnode is an identifier used to group all objects for support of VMS 
sign configurations that are common to all VMS devices. 
<Object Identifier> 1.3.6.1.4.1.1206.4.2.3.2"
::= { dms 2 }

-- 5.3.1	Character Height in Pixels Parameter 
vmsCharacterHeightPixels  OBJECT-TYPE 
SYNTAX      Integer32 (0..255) 
UNITS       "pixels"
MAX-ACCESS  read-only 
STATUS      current  
DESCRIPTION  
"<Definition> Indicates the height of a single character in pixels. The value 
zero (0) indicates a variable character height, which implies a full-matrix 
sign.
<Parameter Type> Status
<Object Identifier> 1.3.6.1.4.1.1206.4.2.3.2.1"
::= { vmsCfg 1 }

-- 5.3.2	Character Width in Pixels Parameter 
vmsCharacterWidthPixels  OBJECT-TYPE 
SYNTAX      Integer32 (0..255) 
UNITS       "pixels"
MAX-ACCESS  read-only 
STATUS      current  
DESCRIPTION  
"<Definition> Indicates the width of a single character in Pixels. The value 
zero (0) indicates a variable character width, which implies either a full-
matrix or line-matrix sign.
<Parameter Type> Status
<Object Identifier> 1.3.6.1.4.1.1206.4.2.3.2.2"
::= { vmsCfg 2 }

-- 5.3.3	Sign Height in Pixels Parameter 
vmsSignHeightPixels  OBJECT-TYPE 
SYNTAX      Integer32 (0..65535) 
UNITS       "pixels"
MAX-ACCESS  read-only 
STATUS      current  
DESCRIPTION  
"<Definition> Indicates the number of rows of pixels for the entire sign.
<Informative> To determine the number of lines for a line matrix or character 
matrix sign, divide the vmsSignHeightPixels object value by the 
vmsCharacterHeightPixels object value. This should result in a whole number, 
the number of lines in the sign.
<Parameter Type> Status
<Object Identifier> 1.3.6.1.4.1.1206.4.2.3.2.3"
::= { vmsCfg 3 }

-- 5.3.4	Sign Width in Pixels Parameter 
vmsSignWidthPixels  OBJECT-TYPE 
SYNTAX      Integer32 (0..65535) 
UNITS       "pixels"
MAX-ACCESS  read-only 
STATUS      current  
DESCRIPTION  
"<Definition> Indicates the number of columns of pixels for the entire sign.
<Informative> To determine the number of characters per line for a character 
matrix sign, divide the vmsSignWidthPixels object value by the 
vmsCharacterWidthPixels object value.
<Parameter Type> Status
<Object Identifier> 1.3.6.1.4.1.1206.4.2.3.2.4" 
::= { vmsCfg 4 }

-- 5.3.5	Horizontal Pitch Parameter 
vmsHorizontalPitch  OBJECT-TYPE 
SYNTAX      Integer32 (0..255) 
UNITS       "millimeters"
MAX-ACCESS  read-only 
STATUS      current  
DESCRIPTION  
"<Definition> Indicates the horizontal distance from the center of one pixel 
to the center of the neighboring pixel in millimeters. The horizontal pitch 
on a character matrix DMS does not apply to the spacing between characters 
but does apply to the distance between pixels within a character.
<Parameter Type> Status
<Object Identifier> 1.3.6.1.4.1.1206.4.2.3.2.5"
::= { vmsCfg 5 }

-- 5.3.6	Vertical Pitch Parameter 
vmsVerticalPitch  OBJECT-TYPE 
SYNTAX      Integer32 (0..255) 
UNITS       "millimeters"
MAX-ACCESS  read-only 
STATUS      current  
DESCRIPTION  
"<Definition> Indicates the vertical distance from the center of one pixel to 
the center of the neighboring pixel in millimeters. The vertical pitch on a 
line matrix DMS does not apply to the spacing between lines but does apply to 
the distance between pixels within a line. The vertical pitch on a character 
matrix DMS does not apply to the spacing between characters but does apply to 
the distance between pixels within a character.
<Parameter Type> Status
<Object Identifier> 1.3.6.1.4.1.1206.4.2.3.2.6"
::= { vmsCfg 6 }

-- 5.3.7	Monochrome Color Parameter 
monochromeColor  OBJECT-TYPE 
SYNTAX      NtcipTwoColors 
MAX-ACCESS  read-only 
STATUS      current  
DESCRIPTION  
"<Definition> Indicates the color supported by a monochrome sign. If the 
'monochrome1Bit' or 'monochrome8Bit' scheme is used, then this object will 
contain six octets. The first 3 octets shall, in this order, indicate the 
red, green, and blue component values of the color when the pixels are turned 
'ON'. The last 3 octets shall, in this order, indicate the red, green, and 
blue component values of the color when the pixels are turned 'OFF'. If the 
sign is a non-monochrome sign, then the value of this object shall be an 
octet string of six zeros (0x00 0x00 0x00 0x00 0x00 0x00). 
<Parameter Type> Status
<Object Identifier> 1.3.6.1.4.1.1206.4.2.3.2.7"
::= { vmsCfg 7 }

-- 5.4	Font Definition Objects 
fontDefinition  OBJECT-IDENTITY 
STATUS  current
DESCRIPTION
"This node is an identifier used to group all objects for DMS font 
configurations that are common to DMS devices. 
<Object Identifier> 1.3.6.1.4.1.1206.4.2.3"
::= { dms 3 }

-- 5.4.1	Maximum Number of Fonts Parameter 
numFonts  OBJECT-TYPE
SYNTAX      Integer32 (0..255)
UNITS       "fonts"
MAX-ACCESS  read-only
STATUS      current
DESCRIPTION 
"<Definition> Indicates the maximum number of fonts that the sign can store. 
See the Specification in association with the supplemental requirements for 
fonts to determine the number of fonts that the DMS must support.
<Parameter Type> Status
<Object Identifier> 1.3.6.1.4.1.1206.4.2.3.3.1"
::= { fontDefinition 1 }

-- 5.4.2	Font Table Parameter 
fontTable  OBJECT-TYPE
SYNTAX      SEQUENCE OF FontEntry
MAX-ACCESS  not-accessible
STATUS      current 
DESCRIPTION "
<Definition> A table containing the information needed to configure/define a 
particular font. Changing an object in a font or character table while the 
font is used by a displayed message yields unpredictable results.
<Informative>  The DMS WG recognizes that the message display on the sign 
could be unpredictable during the download of a font when using the unmanaged 
state (V1 compatibility). Those specifying authorities or application 
developers who are sensitive to this issue can blank the display during a 
font download.
<Table Type> static
<Object Identifier> 1.3.6.1.4.1.1206.4.2.3.3.2"
::= {fontDefinition 2}

fontEntry OBJECT-TYPE
SYNTAX      FontEntry
MAX-ACCESS  not-accessible
STATUS      current 
DESCRIPTION "<Definition> Parameters of the Font Table."
INDEX {fontIndex}
::= {fontTable 1}

FontEntry ::= SEQUENCE{
   fontIndex       Integer32,
   fontNumber      Integer32,
   fontName        SnmpAdminString,
   fontHeight      Integer32,
   fontCharSpacing Integer32,
   fontLineSpacing Integer32,
   fontVersionID   Integer32,
   fontStatus      INTEGER
   } 

-- 5.4.2.1	Font Index Parameter 
fontIndex  OBJECT-TYPE 
SYNTAX      Integer32 (1..255) 
MAX-ACCESS  read-only 
STATUS      current  
DESCRIPTION  
"<Definition> Indicates the row number of the entry. An implementation shall 
support exactly the number of rows defined by numFonts, startng at 1 and be 
sequential.
<Parameter Type> Status
<Object Identifier> 1.3.6.1.4.1.1206.4.2.3.3.2.1.1"
::= { fontEntry 1 }

-- 5.4.2.2	Font Number Parameter 
fontNumber  OBJECT-TYPE 
SYNTAX      Integer32 (1..255) 
MAX-ACCESS  read-write 
STATUS      current 
DESCRIPTION  
"<Definition> A unique, user-specified number for a particular font which can 
be different from the value of the fontIndex-object. This is the number 
referenced by MULTI when specifying a particular font.
<Parameter Type> Configuration
<Object Identifier> 1.3.6.1.4.1.1206.4.2.3.3.2.1.2"
::= { fontEntry 2 }

-- 5.4.2.3	Font Name Parameter 
fontName  OBJECT-TYPE 
SYNTAX      SnmpAdminString (SIZE (0..64)) 
MAX-ACCESS  read-write 
STATUS      current 
DESCRIPTION  
"<Definition> Indicates the name of the font.
<Informative> Prior to NTCIP 1203 v04, this object type only supported NVT-
ASCII characters. New implementations should specify their supported values 
for this object type in their AGENT-CAPABILITIES statement. Attempting to 
store a value that includes characters not supported by an implementation can 
result in an error response. 
<Parameter Type> Configuration
<Object Identifier> 1.3.6.1.4.1.1206.4.2.3.3.2.1.3"
::= { fontEntry 3 }

-- 5.4.2.4	Font Height Parameter 
fontHeight  OBJECT-TYPE 
SYNTAX      Integer32 (0..255) 
UNITS       "pixels"
MAX-ACCESS  read-write 
STATUS      current  
DESCRIPTION  
"<Definition> Indicates the height of the font in pixels. Changing the value 
of this object invalidates this fontTable row, sets all corresponding 
characterWidth objects to zero (0), and sets all corresponding 
characterBitmap objects to zero length. Character Matrix and Line Matrix VMS 
shall subrange this object either to a value of zero (0) or the value of 
vmsCharacterHeightPixels; a Full Matrix VMS shall subrange this object to the 
range of zero (0) to the value of vmsSignHeightPixels or 255, whichever is 
less.
<Parameter Type> Configuration
<Object Identifier> 1.3.6.1.4.1.1206.4.2.3.3.2.1.4"
::= { fontEntry 4 }

-- 5.4.2.5	Font Character Spacing Parameter 
fontCharSpacing  OBJECT-TYPE 
SYNTAX      Integer32 (0..255) 
UNITS       "pixels"
MAX-ACCESS  read-write 
STATUS      current  
DESCRIPTION  
"<Definition> Indicates the default horizontal spacing (in pixels) between 
each of the characters within the font.  If the font changes on a line, then 
the average character spacing of the two fonts, rounded up to the nearest 
whole pixel, shall be used between the two characters where the font changes. 
Character Matrix VMS shall ignore the value of this object; Line Matrix and 
Full Matrix VMS shall subrange this object to the range of zero (0) to the 
smaller of 255 or the value of vmsSignWidthPixels.
See also the MULTI tag 'spacing character [sc]'.
<Parameter Type> Configuration
<Object Identifier> 1.3.6.1.4.1.1206.4.2.3.3.2.1.5"
::= { fontEntry 5 }

-- 5.4.2.6	Font Line Spacing Parameter 
fontLineSpacing  OBJECT-TYPE 
SYNTAX      Integer32 (0..255) 
UNITS       "pixels"
MAX-ACCESS  read-write 
STATUS      current  
DESCRIPTION  
"<Definition> Indicates the default vertical spacing (in pixels) between each 
of the lines within the font for Full Matrix VMS. The line spacing for a line 
is the largest font line spacing of all fonts used on that line. The number 
of pixels between adjacent lines is the average of the 2 line spacings of 
each line, rounded up to the nearest whole pixel. Character Matrix VMS and 
Line Matrix VMS shall ignore the value of this object; Full Matrix VMS shall 
subrange this object to the range of zero (0) to the smaller of 255 or the 
value of vmsSignHeightPixels.
See also the MULTI tag 'new line [nl]'.
<Parameter Type> Configuration
<Object Identifier> 1.3.6.1.4.1.1206.4.2.3.3.2.1.6"
::= { fontEntry 6 }

-- 5.4.2.7	Font Version ID Parameter 
fontVersionID  OBJECT-TYPE 
SYNTAX      Integer32 (0..65535) 
MAX-ACCESS  read-only 
STATUS      current  
DESCRIPTION  
"<Definition> Each font that has been downloaded to a sign shall have a 
relatively unique ID. This ID shall be calculated using the CRC-16 algorithm 
defined in ISO 3309 and the associated OER-encoded (as defined in ITU-T 
X.696) FontVersionByteStream. 
The sign shall respond with the version ID value that is valid at the time.

FontVersionByteStream consists of the main font characteristics followed by n 
rows of CharacterInfoList, as shown by the following ASN.1 construct:  
  FontVersionByteStream ::= SEQUENCE {
        fontInformation    FontInformation,
        characterInfoList  CharacterInfoList }

FontInformation describes the characteristics of the font which are common to 
each character and defines the order in which this information appears when 
constructing the byte stream which will be used to calculate the CRC. There 
is only one row of data for this SEQUENCE for a specific font, as defined by 
the following ASN.1 construct:
  FontInformation ::= SEQUENCE {
        fontNumber            INTEGER (1..255),
        fontHeight            INTEGER (0..255),
        fontCharSpacing       INTEGER (0..255),
        fontLineSpacing       INTEGER (0..255) }

CharacterInfoList describes the characteristics of each defined character 
(e.g., where characterWidth is greater than 0) for the fontNumber indicated 
within the fontInformation field. The CharacterInformation is ordered by the 
characterNumber in an increasing format per the following ASN.1 construct:
  CharacterInfoList ::=  SEQUENCE OF CharacterInformation

CharacterInformation describes the characteristics of a single character and 
defines the objects and order of the objects within one row of 
CharacterInfoList, per the following ASN.1 construct: 
  CharacterInformation  SEQUENCE {
      characterNumber         INTEGER (1..65535),
      characterWidth          INTEGER (0..255),
      characterBitmap         OCTET STRING }

Complete definitions for these referenced objects are contained elsewhere in 
this document.

The following is an example of developing the FontVersionByteStream value. 
Assume the following values for this example, where we only have 2 characters 
defined:
fontNumber = 2, 
fontHeight = 7, 
fontCharSpacing = 1, 
fontLineSpacing = 3, 
characterWidth.52 = 7, 
characterBitmap.52 = 1C 59 34 6F E1 83 00, 
characterWidth.65 = 6, 
characterBitmap.65 = 7B 3C FF CF 3C C0 

The resulting string in hex would be:
FontVersionByteStream = 02 07 01 03 01 02 00 34 07 07 1C 59 34 6F E1 83 00 00 
41 06 06 7B 3C FF CF 3C C0, i.e.,:  
02                   fontNumber
07                   fontHeight
01                   fontCharSpacing
03                   fontLineSpacing
01                   length of the count field
02                   count of entries in CharacterInfoList
00 34                characterNumber
07                   characterWidth
07                   length of characterBitmap
1C 59 34 6F E1 83 00 characterBitmap
00 41                characterNumber
06                   characterWidth
06                   length of characterBitmap
7B 3C FF CF 3C C0    characterBitmap

CRC = 0x52ED
fontVersionID = 0xED52

Clarifications: 
 a) characterNumber is a two-byte unsigned integer.
 b) characterBitmap is defined as OCTET STRING without a size constraint. 
(the length octets shall be present)
 c) CharacterInfoList is defined as SEQUENCE-OF that requires a quantity 
field (unconstrained unsigned integer) 'with a value equal to the number of 
times the componentType is repeated within the value field'.

The resulting graphic depictions of those 2 defined characters are:
0001110
0010110
0100110
1000110
1111111
0000110
0000110

and

011110
110011
110011
111111
110011
110011
110011

The ASN.1 playground (https://asn1.io/asn1playground/) can be used to produce 
example encodings.
<Parameter Type> Status
<Object Identifier> 1.3.6.1.4.1.1206.4.2.3.3.2.1.7"
::= { fontEntry 7 }

-- 5.4.2.8	Font Status Parameter 
fontStatus  OBJECT-TYPE 
SYNTAX      INTEGER {
                 notUsed (1),
                 modifying (2),
                 calculatingID (3),
                 readyForUse (4),  
                 inUse (5),
                 permanent (6),
                 modifyReq (7),
                 readyForUseReq (8),
                 notUsedReq (9),
                 unmanagedReq (10), -- obsolete
                 unmanaged (11)}    -- obsolete 
MAX-ACCESS  read-write 
STATUS      current  
DESCRIPTION  
"<Definition> This object defines a state machine allowing to manage fonts 
stored within a DMS. 
<Format> The definitions of the possible values are:
notUsed (1) - a state indicating that this row in this table is currently not 
used.
modifying (2) - a state indicating that the objects defined in this row can 
be modified. 
calculatingID (3) - a state indicating that the  fontVersionID for this row 
is currently being calculated.
readyForUse (4) - a state indicating that the font defined in this row can be 
used  for message display.
inUse (5) - a state indicating that the font defined in this row is currently 
being used for the displayed message.
permanent (6) - a state indicating that the font defined in this row is a 
permanent font that cannot be modified. This font is provided by the sign 
vendor and can be used for message display.
modifyReq (7) -  command sent to request the transition to the modifying 
state..
readyForUseReq (8) -  command sent to request the transition to the 
readyForUse state.
notUsedReq (9) -  command sent to request the transition to the notUsed 
state.
unmanagedReq (10) -  command sent to request the transition to the unmanaged 
state.
unmanaged (11) - a state indicating that the font defined in this row is a 
font that is not managed using the fontStatus object. This state can be used 
to manage the font as in NTCIP 1203 v1. 
<Informative> The fontStatus object was added in version 2; the values of 
'unmanagedReq' and 'unmanaged' were provided for backwards compatibility with 
version 1 devices. With the introduction of SNMPv3 in NTCIP 1203 v04, 
backwards compatibility is lost and these two values are considered obsolete. 
<Parameter Type> Configuration
<Object Identifier> 1.3.6.1.4.1.1206.4.2.3.3.2.1.8"
::= { fontEntry 8 }

-- 5.4.3	Maximum Characters per Font Parameter 
maxFontCharacters  OBJECT-TYPE 
SYNTAX      Integer32 (1..65535) 
UNITS       "characters"
MAX-ACCESS  read-only 
STATUS      current  
DESCRIPTION  
"<Definition> Indicates the maximum number of rows in the character table 
that can exist for any given font. 
<Parameter Type> Status
<Object Identifier> 1.3.6.1.4.1.1206.4.2.3.3.3"
::= { fontDefinition 3 }

-- 5.4.4	Character Table Parameter 
characterTable  OBJECT-TYPE 
SYNTAX      SEQUENCE OF CharacterEntry
MAX-ACCESS  not-accessible
STATUS      current
DESCRIPTION "<Definition> A table containing the information needed to 
configure/define each character of a particular font.
<Table Type> static
<Object Identifier> 1.3.6.1.4.1.1206.4.2.3.3.4"
::= {fontDefinition 4}

characterEntry OBJECT-TYPE
SYNTAX      CharacterEntry
MAX-ACCESS  not-accessible
STATUS      current
DESCRIPTION "<Definition> Parameters of the Character Configuration Table."
INDEX {fontIndex, characterNumber}
::= {characterTable 1}

CharacterEntry ::= SEQUENCE {
   characterNumber   Integer32,
   characterWidth    Integer32,
   characterBitmap   OCTET STRING} 

-- 5.4.4.1	Character Number Parameter 
characterNumber  OBJECT-TYPE 
SYNTAX      Integer32 (1..65535) 
MAX-ACCESS  read-only 
STATUS      current 
DESCRIPTION  
"<Definition> Indicates the code point associated with this character of this 
font. 
<Informative>For example, if the font set followed the ASCII or Unicode 
numbering schemes, the character giving the bitmap of 'A' would be 
characterNumber 65 and would be encoded as 0x41 in a MULTI string (in either 
the eightBit or utf8Style encoding). Likewise, if the font set followed the 
Unicode numbering scheme, the character giving the bitmap of the British 
pound sign would be character number 163. A MULTI string accessing this 
character would use the code 0xA3 if using eightBit encoding and would use 
0xC2A3 if using the utf8Style encoding. Code points above 255 can only be 
accessed in the eightBit encoding scheme by using the hexadecimal character 
tag (e.g., [hc0100] to display character 256); the UTF8Style is able to 
encode all 65,535 potential characters supported by a single font within 3 
octets
<Parameter Type> Status
<Object Identifier> 1.3.6.1.4.1.1206.4.2.3.3.4.1.1"
::= { characterEntry 1 }

-- 5.4.4.2	Character Width Parameter 
characterWidth  OBJECT-TYPE
SYNTAX      Integer32 (0..255) 
UNITS       "pixels" 
MAX-ACCESS  read-write 
STATUS      current  
DESCRIPTION  
"<Definition> Indicates the width of this character in pixels. A width of 
zero (0) indicates this row is invalid. A Character Matrix VMS shall subrange 
this object either to a value of zero (0) or the value of the 
vmsCharacterWidthPixels object; a Line Matrix or Full Matrix VMS shall 
subrange this object to a range of zero (0) to vmsSignWidthPixels. 
<Parameter Type> Configuration
<Object Identifier> 1.3.6.1.4.1.1206.4.2.3.3.4.1.2"
::= { characterEntry 2 }

-- 5.4.4.3	Character Bitmap Parameter 
characterBitmap  OBJECT-TYPE 
SYNTAX      OCTET STRING 
MAX-ACCESS  read-write 
STATUS      current 
DESCRIPTION  
"<Definition> A bitmap that defines each pixel within a rectangular region as 
being either displayed in the foreground color (bit=1) or transparent 
(bit=0). If the pixel is transparent, it will remain whatever color existed 
in the message before drawing the character. This might be the background 
color, a color rectangle (see MULTI tag) or a graphic. The result of this 
bitmap is how the character appears on the sign.

The octet string is treated as a binary bit string. The most significant bit 
defines the state of the pixel in the upper left corner of the rectangular 
region. The rectangular region is processed by rows, left to right, then top 
to bottom. The size of the rectangular region is defined by the fontHeight 
and characterWidth objects; any remaining bits shall be ignored, except for 
use in the calculation of the CRC. 

This object shall be subranged by the device to the maximum number of bytes 
as indicated by fontMaxCharacterSize. 

<Informative>Version 1 Compatibility:  Version 1 of this standard defined the 
bits as ON (foreground color) or OFF (background color). 
<Parameter Type> Configuration
<Object Identifier> 1.3.6.1.4.1.1206.4.2.3.3.4.1.3"
::= { characterEntry 3 }

-- 5.4.5	Maximum Character Size Parameter
fontMaxCharacterSize  OBJECT-TYPE
SYNTAX      Integer32 (0..65535) 
UNITS       "octets" 
MAX-ACCESS  read-only 
STATUS      current  
DESCRIPTION  
"<Definition> An indication of the maximum size, in octets, that the DMS 
supports for each character's characterBitmap object.

The largest value of this object must be equal to or smaller than the value 
defined by ROUNDUP(total number of pixels of the sign / 8).
<Parameter Type> Status
<Object Identifier> 1.3.6.1.4.1.1206.4.2.3.3.5"
::= { fontDefinition 5 }

-- 5.5	Multi-Configuration Objects 
multiCfg  OBJECT-IDENTITY 
STATUS  current
DESCRIPTION
"<Definition> This subnode is an identifier used to group all objects for 
support of MULTI language configuration such as all default tag values. 
<Object Identifier> 1.3.6.1.4.1.1206.4.2.3.4"
::= { dms 4 }

-- 5.5.1	Default Background Color Parameter 
defaultBackgroundColor  OBJECT-TYPE 
SYNTAX      DmsClassicColor 
MAX-ACCESS  read-write 
STATUS      deprecated  
DESCRIPTION  
"<Definition> Indicates the color of the background shown on the sign for the 
'colorClassic' scheme (see the dmsColorScheme object). If a different color 
scheme is used, a genErr shall be returned. If a color is requested that is 
not supported, then a genErr shall be returned. 
<Superseded by> defaultBackgroundRGB
<Informative> This object was deprecated in v04 and should not be used in 
native SNMPv3 implementations.
<Parameter Type> Configuration
<Object Identifier> 1.3.6.1.4.1.1206.4.2.3.4.1"
DEFVAL  { black } 
::= { multiCfg 1 }

-- 5.5.2	Default Foreground Color Parameter 
defaultForegroundColor  OBJECT-TYPE 
SYNTAX      DmsClassicColor 
MAX-ACCESS  read-write 
STATUS      deprecated  
DESCRIPTION  
"<Definition> Indicates the color of the foreground (the actual text) shown 
on the sign for the 'colorClassic' scheme (see the dmsColorScheme object). If 
a different color scheme is used, a genErr shall be returned. If a color is 
requested that is not supported, then a genErr shall be returned.
<Superseded by> defaultForegroundRGB
<Informative> This object was deprecated in v04 and should not be used in 
native SNMPv3 implementations.
<Parameter Type> Configuration
<Object Identifier> 1.3.6.1.4.1.1206.4.2.3.4.2"
::= { multiCfg 2 }

-- 5.5.3	Default Flash On Time Parameter 
defaultFlashOn  OBJECT-TYPE 
SYNTAX      Integer32 (0..255)
UNITS       "tenths of a second" 
MAX-ACCESS  read-write 
STATUS      current  
DESCRIPTION  
"<Definition> Indicates the default flash on time, in tenths of a second, for 
flashing text. If the time is set to zero (0), the default is NO FLASHing but 
the text remains visible. This object may be sub-ranged by an implementation; 
see Section 3.5.2.2.2.3 for more information.
<Parameter Type> Configuration
<Object Identifier> 1.3.6.1.4.1.1206.4.2.3.4.3"
DEFVAL  {5} 
::= { multiCfg 3 }

-- 5.5.4	Default Flash On Time Parameter at Activation 
defaultFlashOnActivate  OBJECT-TYPE 
SYNTAX      Integer32 (0..255)
UNITS       "tenths of a second" 
MAX-ACCESS  read-only 
STATUS      current  
DESCRIPTION  
"<Definition> Indicates the value of defaultFlashOn at activation of the 
currently active message for the purpose of determining what the value was at 
the time of activation. The value shall be created (overwritten) at the time 
when the message was copied into the currentBuffer.
If the implementation supports dmsShortPowerRecoveryMessage, 
dmsLongPowerRecoveryMessage, or dmsResetMessage this parameter shall be 
stored in non-volatile memory so that it can be referenced if any of those 
objects are set to currentBuffer.
<Parameter Type> Status
<Object Identifier> 1.3.6.1.4.1.1206.4.2.3.4.17"
::= { multiCfg 17 }

-- 5.5.5	Default Flash Off Time Parameter 
defaultFlashOff  OBJECT-TYPE 
SYNTAX      Integer32 (0..255)
UNITS       "tenths of a second" 
MAX-ACCESS  read-write 
STATUS      current  
DESCRIPTION  
"<Definition> Indicates the default flash off time, in tenths of a second, 
for flashing text. If the time is set to zero (0), the default is NO FLASHing 
but the text remains visible. This object may be sub-ranged by an 
implementation; see Section 3.5.2.2.2.3 for more information.
<Parameter Type> Configuration
<Object Identifier> 1.3.6.1.4.1.1206.4.2.3.4.4"
DEFVAL  {5} 
::= { multiCfg 4 }

-- 5.5.6	Default Flash Off Time Parameter at Activation 
defaultFlashOffActivate  OBJECT-TYPE 
SYNTAX      Integer32 (0..255)
UNITS       "tenths of a second" 
MAX-ACCESS  read-only 
STATUS      current  
DESCRIPTION  
"<Definition> Indicates the value of defaultFlashOff at activation of the 
currently active message for the purpose of determining what the value was at 
the time of activation. The value shall be created (overwritten) at the time 
when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.18"
::= { multiCfg 18 }

-- 5.5.7	Default Font Parameter 
defaultFont  OBJECT-TYPE 
SYNTAX      Integer32 (1..255) 
MAX-ACCESS  read-write 
STATUS      current 
DESCRIPTION  
"<Definition> Indicates the default font number (fontNumber-object) for a 
message. 
<Parameter Type> Configuration
<Object Identifier> 1.3.6.1.4.1.1206.4.2.3.4.5"
DEFVAL  {1} 
::= { multiCfg 5 }

-- 5.5.8	Default Font Parameter at Activation 
defaultFontActivate  OBJECT-TYPE 
SYNTAX      Integer32 (1..255) 
MAX-ACCESS  read-only 
STATUS      current 
DESCRIPTION  
"<Definition> Indicates the value of defaultFont at activation of the 
currently active message for the purpose of determining what the value was at 
the time of activation. The value shall be created (overwritten) at the time 
when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.19"
::= { multiCfg 19 }

-- 5.5.9	Default Line Justification Parameter 
defaultJustificationLine  OBJECT-TYPE 
SYNTAX      INTEGER {
                 other(1), -- retired
                 left(2),
                 center(3),
                 right(4),
                 full(5) } 
MAX-ACCESS  read-write 
STATUS      current 
DESCRIPTION  
"<Definition> Indicates the default line justification for a message. This 
object may be sub-ranged by an implementation; see Section 3.5.2.2.2.5 for 
more information.
<Informative> In v02, the enumerated value of 'other' is RETIRED to improve 
interoperability.
<Parameter Type> Configuration
<Object Identifier> 1.3.6.1.4.1.1206.4.2.3.4.6"
DEFVAL  {center} 
::= { multiCfg 6 }

-- 5.5.10	Default Line Justification Parameter at Activation 
defaultJustificationLineActivate  OBJECT-TYPE 
SYNTAX      INTEGER {
                 left(2),
                 center(3),
                 right(4),
                 full(5) } 
MAX-ACCESS  read-only 
STATUS      current  
DESCRIPTION  
"<Definition> Indicates the value of defaultJustificationLine at activation 
of the currently active message for the purpose of determining what the value 
was at the time of activation. The value shall be created (overwritten) at 
the time when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.20"
::= { multiCfg 20 }

-- 5.5.11	Default Page Justification Parameter 
defaultJustificationPage  OBJECT-TYPE 
SYNTAX      INTEGER {
                 --other(1), -retired
                 top(2),
                 middle(3),
                 bottom(4) } 
MAX-ACCESS  read-write 
STATUS      current  
DESCRIPTION  
"<Definition> Indicates the default page justification for a message. This 
object may be sub-ranged by an implementation; see Section 3.5.2.2.2.6 for 
more information.
<Informative> In v02, the enumerated value of 'other' is RETIRED to improve 
interoperability.
<Parameter Type> Configuration
<Object Identifier> 1.3.6.1.4.1.1206.4.2.3.4.7"
DEFVAL  {middle} 
::= { multiCfg 7 }

-- 5.5.12	Default Page Justification Parameter at Activation 
defaultJustificationPageActivate  OBJECT-TYPE 
SYNTAX      INTEGER {
                 top(2),
                 middle(3),
                 bottom(4) } 
MAX-ACCESS  read-only 
STATUS      current  
DESCRIPTION  
"<Definition> Indicates the value of defaultJustificationPage at activation 
of the currently active message for the purpose of determining what the value 
was at the time of activation. The value shall be created (overwritten) at 
the time when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.21"
::= { multiCfg 21 }

-- 5.5.13	Default Page On Time Parameter 
defaultPageOnTime  OBJECT-TYPE 
SYNTAX      Integer32 (1..255)
UNITS       "tenths of a second" 
MAX-ACCESS  read-write 
STATUS      current  
DESCRIPTION  
"<Definition> Indicates the default page on time, in tenths (1/10) of a 
second. If the message is only one page, this value is ignored, and the page 
is continuously displayed. This object may be sub-ranged by an 
implementation; see Section 3.5.2.2.2.7 for more information.
<Parameter Type> Configuration
<Object Identifier> 1.3.6.1.4.1.1206.4.2.3.4.8"
DEFVAL  {30} 
::= { multiCfg 8 }

-- 5.5.14	Default Page On Time Parameter at Activation 
defaultPageOnTimeActivate  OBJECT-TYPE 
SYNTAX      Integer32 (1..255)
UNITS       "tenths of a second" 
MAX-ACCESS  read-only 
STATUS      current  
DESCRIPTION  
"<Definition> Indicates the value of defaultPageOnTime at activation of the 
currently active message for the purpose of determining what the value was at 
the time of activation. The value shall be created (overwritten) at the time 
when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.22"
::= { multiCfg 22 }

-- 5.5.15	Default Page Off Time Parameter 
defaultPageOffTime  OBJECT-TYPE 
SYNTAX      Integer32 (0..255)
UNITS       "tenths of a second" 
MAX-ACCESS  read-write 
STATUS      current  
DESCRIPTION  
"<Definition> Indicates the default page off time, in tenths (1/10) of a 
second. If the message is only one page, this value is ignored, and the page 
is continuously displayed. This object may be sub-ranged by an 
implementation; see Section 3.5.2.2.2.7 for more information.
<Parameter Type> Configuration
<Object Identifier> 1.3.6.1.4.1.1206.4.2.3.4.9"
DEFVAL  {0} 
::= { multiCfg 9 }

-- 5.5.16	Default Page Off Time Parameter at Activation 
defaultPageOffTimeActivate  OBJECT-TYPE 
SYNTAX      Integer32 (0..255)
UNITS       "tenths of a second" 
MAX-ACCESS  read-only 
STATUS      current  
DESCRIPTION  
"<Definition> Indicates the value of defaultPageOffTime at activation of the 
currently active message for the purpose of determining what the value was at 
the time of activation. The value shall be created (overwritten) at the time 
when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.23"
::= { multiCfg 23 }

-- 5.5.17	Default Background Color RGB Parameter 
defaultBackgroundRGB  OBJECT-TYPE 
SYNTAX      DmsColor  
MAX-ACCESS  read-write 
STATUS      current  
DESCRIPTION  
"<Definition> Indicates the color of the background shown on the sign if not 
changed by the 'Page Background Color' MULTI tag or the 'Color Rectangle' 
MULTI tag. 

This object may be sub-ranged by an implementation; see Section 3.5.2.2.2.2 
for more information. If a color is requested that is not supported, then a 
wrongValue error shall be returned. 

If the dmsColorScheme is monochrome8bit, the DMS shall accept any single 
octet value and will transpose and store the value to the closest value that 
the sign supports (i.e., the sign does not have to support all 255 levels of 
illumination). If dmsColorScheme is colorClassic, the DMS shall only accept 
values supported by the DMS. If the value is color24bit, the DMS shall accept 
any three-octet value and will transpose and store the value to the closest 
value that the sign supports (i.e., the sign does not have to support all 
possible color combinations).

<Parameter Type> Configuration
<Object Identifier> 1.3.6.1.4.1.1206.4.2.3.4.12"
::= { multiCfg 12 }

-- 5.5.18	Default Background Color RGB Parameter at Activation 
defaultBackgroundRGBActivate  OBJECT-TYPE 
SYNTAX      DmsColor 
MAX-ACCESS  read-only 
STATUS      current  
DESCRIPTION  
"<Definition> Indicates the value of defaultBackgroundRGB at activation of 
the currently active message for the purpose of determining what the value 
was at the time of activation. The value shall be created (overwritten) at 
the time when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.24"
::= { multiCfg 24 }

-- 5.5.19	Default Foreground Color RGB Parameter 
defaultForegroundRGB  OBJECT-TYPE 
SYNTAX      DmsColor 
MAX-ACCESS  read-write 
STATUS      current  
DESCRIPTION  
"<Definition> Indicates the color of the foreground shown on the sign unless 
changed by the 'Color Foreground' MULTI tag. This is the color used to 
illuminate the 'ON' pixels of displayed characters. 

This object may be sub-ranged by an implementation; see Section 3.5.2.2.2.2 
for more information. If a color is requested that is not supported, then a 
wrongValue error shall be returned. 

If the dmsColorScheme is monochrome8bit, the DMS shall accept any single 
octet value and will transpose and store the value to the closest value that 
the sign supports (i.e., the sign does not have to support all 255 levels of 
illumination). If dmsColorScheme is colorClassic, the DMS shall only accept 
values supported by the DMS. If the value is color24bit, the DMS shall accept 
any three-octet value and will transpose and store the value to the closest 
value that the sign supports (i.e., the sign does not have to support all 
possible color combinations).

<Parameter Type> Configuration
<Object Identifier> 1.3.6.1.4.1.1206.4.2.3.4.13"
::= { multiCfg 13 }

-- 5.5.20	Default Foreground Color RGB Parameter at Activation
defaultForegroundRGBActivate  OBJECT-TYPE 
SYNTAX      DmsColor 
MAX-ACCESS  read-only 
STATUS      current 
DESCRIPTION  
"<Definition> Indicates the value of defaultForegroundRGB at activation of 
the currently active message for the purpose of determining what the value 
was at the time of activation. The value shall be created (overwritten) at 
the time when the message was copied into the currentBuffer.
If the implementation supports dmsShortPowerRecoveryMessage 
dmsLongPowerRecoveryMessage, or dmsResetMessage, this parameter shall be 
stored in non-volatile memory so that it can be referenced if any of those 
objects are set to currentBuffer.
<Parameter Type> Status
<Object Identifier> 1.3.6.1.4.1.1206.4.2.3.4.25"
::= { multiCfg 25 }

-- 5.5.21	Default Character Set Parameter 
defaultCharacterSet  OBJECT-TYPE 
SYNTAX      INTEGER {
                 other (1),
                 eightBit (2),
                 utf8Style (3)} 
MAX-ACCESS  read-write 
STATUS      current  
DESCRIPTION  
"<Definition> Indicates the algorithm used to encode each characterNumber 
within a MULTI string.
<Format>
  other (1): a read-only value indicating an encoding scheme other than those 
listed below, refer to the device manual. Implementations that support other 
encodings shall provide a parallel manufacturer-specific object that provides 
a read-only enumeration for 'standard' along with any custom enumerations.  A 
set to the parallel manufacturer-specific object shall cause this object to 
transition to 'other' and a set of this object shall cause the parallel 
manufacturer-specific object to transition to 'standard'.
  eightBit (2): each characterNumber of the current font is encoded as an 8-
bit unsigned integer. This encoding scheme only supports native 
representation of character numbers 1 through 255. Higher character numbers 
can only be displayed using the hexadecimal character tag ([hcx]).
  utf8Style (4): each characterNumber of the current font is encoded as if it     
were a Unicode codepoint encoded according to the rules of UTF-8     
(however, there is no verification that the character bitmap actually     
resembles the character defined by that code point). However, as the font     
table is limited to 65,535 characters, only codes up to 3-octets in     
length are supported. These rules can be summarized as follows: 
    - Values less than 128 are encoded in the 7 available bits in 
      the mask '0xxx xxxx';
    - Values greater than 127 but less than 2048 are encoded in the 
      eleven available bits of the mask '110x xxxx 10xx xxxx'; and 
    - Remaining values are ecoded in the 16 available bits in the 
      mask '1110 xxxx 10xx xxxx 10xx xxxx' 
    - This format does not support 4-octet UTF-8 codes because each
      font is limited to 65535 characters.

This object may be sub-ranged by an implementation (e.g., an implementation 
might only support eightBit encoding); see Section 3.5.2.2.2.8 for more 
information.
<Informative>  
The eightBit and utf8Style formats are conceptually similar to well-known 
encoding formats (i.e., ASCII and UTF-8) but allow the fonts to be customized 
by the user through the use of the font table so that different signs can 
produce similar glyphs (i.e., to define the pixel-level representation of 
each character). However, it is important to note that the resulting 
multistring does not necessarily reflect a genuine ASCII or UTF-8 string, as 
there is no guarantee that the character bitmaps called by the multistring 
will correspond to the conceptual characters identified by their ASCII and 
Unicode codepoints.
Example 1: A MULTI string with an encoded value of 0x41 E2 9C 8B, 
would be decoded as follows according to the different encoding 
schemes: 
  eightBit: four 8-bit characters with codes 65, 226, 156, and 139
  utf8Style: an 8-bit character followed by a 24-bit character. The 
    first character is code 65 and the second character is:
      E    2    9    C    8    B     in hex
    1110 0010 1001 1100 1000 1011    in binary
         0010   01 1100   00 1011    removing mask
              0010 0111 0000 1011    compressing
                2    7    0    B     in hex
                             9995    in decimal

Example 2: The MULTI string  '[fo2]', which is a tag to indicate font 2, is 
encoded as '0x5b 66 6f 32 5d' in both the eightBit and utf8Style encoding 
(i.e., all characters have codes less than 128)
 
Example 3: While it is often convenient to align characterNumbers and 
characterBitmaps with ASCII or UTF-8 character codes, this is not a 
requirement. For example, Character 65 in one font might represent the letter 
'A', but in another font it can represent the grinning face emoticon. As 
such, any character bitmap (including those represented by Unicode codepoints 
greater than 65535) can be defined and supported for display.
 
Example 4: Per the rules of Multistring syntax, the left and right bracket 
characters ('[' and ']') are reserved for tags and to display either, the 
character must appear two times in a row within the MULTI string. Thus, to 
display '[', the MULTI string would be '0x5b5b' for both 'eightBit' and 
'utf8Style' encoding.
<Parameter Type> Configuration
<Object Identifier> 1.3.6.1.4.1.1206.4.2.3.4.10"
DEFVAL  {eightBit} 
::= { multiCfg 10 }

-- 5.5.22	Color Scheme Parameter 
dmsColorScheme  OBJECT-TYPE 
SYNTAX      DmsColorScheme  
MAX-ACCESS  read-only 
STATUS      current  
DESCRIPTION  
"<Definition> Indicates the color scheme for pixels supported by the DMS. 

DMS with dmsColorScheme set to color24bit shall interpret MULTI tags with a 
single color parameter (e.g. [cfx]) according to the codes defined in 
DmsClassicColor.
<Parameter Type> Status
<Object Identifier> 1.3.6.1.4.1.1206.4.2.3.4.11"
DEFVAL  { monochrome1bit } 
::= { multiCfg 11 }

-- 5.5.23	Supported MULTI Tags Parameter
dmsSupportedMultiTags  OBJECT-TYPE 
SYNTAX      OCTET STRING (SIZE (4))
MAX-ACCESS  read-only 
STATUS      deprecated  
DESCRIPTION  
"<Definition> An indication of the MULTI Tags supported by the device. This 
object is a bitmap representation of tag support. 
<Format>
Bit 0 : color background[cbx] / [cbr,g,b] -- deprecated
Bit 1 : color foreground[cfx] / [cfr,g,b]
Bit 2 : flashing[fltxoy] / [floytx]
Bit 3 : font[fox] / [fox,cccc] 
Bit 4 : graphic [gn] / [gn,x,y] / [gn,x,y,cccc] 
Bit 5 : hexadecimal character[hcx] 
Bit 6 : justification line[jlx] 
Bit 7 : justification page[jpx] 
Bit 8 : manufacturer specific[msx,y] 
Bit 9 : moving text[mvtdw,s,r,text] 
Bit 10 : new line[nlx] 
Bit 11 : new page[np] 
Bit 12 : page time[ptxoy] 
Bit 13 : spacing character[scx] 
Bit 14 : field local time 12 hour[f1] 
Bit 15 : field local time 24 hour[f2] 
Bit 16 : ambient temperature Celsius[f3] 
Bit 17 : ambient temperature Fahrenheit[f4] 
Bit 18 : speed km/h[f5] 
Bit 19 : speed m/h[f6] 
Bit 20 : day of week[f7] 
Bit 21 : date of month[f8] 
Bit 22 : month of year[f9] 
Bit 23 : year 2 digits[f10] 
Bit 24 : year 4 digits[f11] 
Bit 25 : local time 12 hour AM/PM[f12] 
Bit 26 : local time 12 hour am/pm[f13]
Bit 27 : text rectangle [trx,y,w,h]
Bit 28 : color rectangle [crx,y,w,h,z] / [crx,y,w,h,r,g,b]
Bit 29 : Page  background [pbz] / [pbr,g,b]
<Superseded by> dmsSupportedMultiTagsV4
<Informative> This object was deprecated in NTCIP 1203 v04 due to ambiguities 
in the bit ordering.
<Parameter Type> Status
<Object Identifier> 1.3.6.1.4.1.1206.4.2.3.4.14"
::= { multiCfg 14 }

-- 5.5.24	Maximum Number of Pages Parameter
dmsMaxNumberPages  OBJECT-TYPE 
SYNTAX      Integer32 (1..255)
UNITS       "pages" 
MAX-ACCESS  read-only 
STATUS      current 
DESCRIPTION  
"<Definition> Indicates the maximum number of pages allowed in the 
dmsMessageMultiString.
<Parameter Type> Status
<Object Identifier> 1.3.6.1.4.1.1206.4.2.3.4.15"
::= { multiCfg 15 }

-- 5.5.25	Maximum MULTI String Length Parameter
dmsMaxMultiStringLength  OBJECT-TYPE 
SYNTAX      Integer32 (0..65535)
UNITS       "octets" 
MAX-ACCESS  read-only 
STATUS      current  
DESCRIPTION  
"<Definition> Indicates the maximum number of octets allowed within the 
dmsMessageMultiString.
<Parameter Type> Status
<Object Identifier> 1.3.6.1.4.1.1206.4.2.3.4.16"
::= { multiCfg 16 }

-- 5.5.26	Supported MULTI Tags Parameter Version 4
dmsSupportedMultiTagsV4  OBJECT-TYPE 
SYNTAX      BITS { colorBackground (0),
                   colorForeground (1),
                   flashing (2),
                   font (3),
                   graphic (4),
                   hexadecimal (5),
                   justificationLine (6),
                   justificationPage (7),
                   manufacturerSpecific (8),
                   movingText (9),
                   newLine (10),
                   newPage (11),
                   pageTime (12),
                   spacingCharacter (13),
                   localTime12hour (14),
                   localTime24hour (15),
                   temperatureCelsius (16),
                   temperatureFahrenheit (17),
                   speedKPH (18),
                   speedMPH (19),
                   dayOfWeek (20),
                   dateOfMonth (21),
                   monthOfYear (22),
                   year2digit (23),
                   year4digit (24),
                   time12hourAMPM (25),
                   time12hourampm (26),
                   textRectangle (27),
                   colorRectangle (28),
                   pageBackground (29) }
MAX-ACCESS  read-only 
STATUS      current  
DESCRIPTION  
"<Definition> An indication of the MULTI Tags supported by the device. This 
object is a bitmap representation of tag support. 
<Valid Value Rule>
colorBackground: [cbx] / [cbr,g,b] -- deprecated
colorForeground: [cfx] / [cfr,g,b]
flashing: [fltxoy] / [floytx]
font: [fox] / [fox,cccc] 
graphic: [gn] / [gn,x,y] / [gn,x,y,cccc] 
hexadecimal: character[hcx] 
justificationLine:[jlx] 
justificationPage: [jpx] 
manufacturerSpecific: [msx,y] 
movingText: [mvtdw,s,r,text] 
newLine: [nlx] 
newPage: [np] 
pageTime: [ptxoy] 
spacingCharacter: [scx] 
localTime12hour: [f1] 
localTime24hour: [f2] 
temperatureCelsius: [f3] 
temperatureFahrenheit: [f4] 
speedKPH: [f5] 
speedMPH: [f6] 
dayOfWeek: [f7] 
dateOfMonth: [f8] 
monthOfYear: [f9] 
year2digits: [f10] 
year4digits: [f11] 
time12hourAMPM: [f12] 
time12hourampm: [f13]
textRectangle: [trx,y,w,h]
colorRectangle: [crx,y,w,h,z] / [crx,y,w,h,r,g,b]
pageBackground: [pbz] / [pbr,g,b]
<Informative> [cbx] and [cbr,g,b] were deprecated in v02 but the bit 
assignment can still be used to indicate support for these deprecated codes.
For example, the value 0x60 00 00 04 has Bits 1, 2, and 29 set, indicating 
support for colorForeground, flashing, and pageBackground.
<Parameter Type> Status
<Object Identifier> 1.3.6.1.4.1.1206.4.2.3.4.17"
::= { multiCfg 26 }

-- 5.6	Message Objects 
dmsMessage  OBJECT-IDENTITY 
STATUS  current
DESCRIPTION
"<Definition> This node is an identifier used to group all objects for 
support of DMS Message Table functions that are common to DMS devices.
<Object Identifier> 1.3.6.1.4.1.1206.4.2.3.5"
::= { dms 5 }

-- 5.6.1	Number of Permanent Messages Parameter 
dmsNumPermanentMsg  OBJECT-TYPE 
SYNTAX      Integer32 (0..65535)
UNITS       "messages" 
MAX-ACCESS  read-only 
STATUS      current  
DESCRIPTION  
"<Definition> Indicates the current number of Messages stored in non-
volatile, non-changeable memory (e.g., EPROM). For CMS and BOS, this is the 
number of different messages that can be assembled.
See the Specifications in association with Requirement 3.6.7.1 to determine 
the messages that must be supported.
<Parameter Type> Status
<Object Identifier> 1.3.6.1.4.1.1206.4.2.3.5.1"
::= { dmsMessage 1 }

-- 5.6.2	Number of Changeable Messages Parameter 
dmsNumChangeableMsg  OBJECT-TYPE 
SYNTAX      Integer32 (0..65535)
UNITS       "messages" 
MAX-ACCESS  read-only 
STATUS      current  
DESCRIPTION  
"<Definition> Indicates the current number of valid Messages stored in non-
volatile, changeable memory. For CMS and BOS, this number shall be zero (0).
<Parameter Type> Status
<Object Identifier> 1.3.6.1.4.1.1206.4.2.3.5.2"
::= { dmsMessage 2 }

-- 5.6.3	Maximum Number of Changeable Messages Parameter 
dmsMaxChangeableMsg  OBJECT-TYPE 
SYNTAX      Integer32 (0..65535)
UNITS       "messages" 
MAX-ACCESS  read-only 
STATUS      current  
DESCRIPTION  
"<Definition> Indicates the maximum number of Messages that the sign can 
store in non-volatile, changeable memory. For CMS and BOS, this number shall 
be zero (0).
See the Specifications in association with Requirement 3.6.7.2 to determine 
the messages that must be supported.
<Informative> This value is intended to be static indicating the maximum 
number of messages that the table allows for the changeable (3) message type.
<Parameter Type> Status
<Object Identifier> 1.3.6.1.4.1.1206.4.2.3.5.3"
::= { dmsMessage 3 }

-- 5.6.4	Free Bytes within Changeable Memory Parameter 
dmsFreeChangeableMemory  OBJECT-TYPE 
SYNTAX      Integer32 (0..2147483647)
UNITS       "octets" 
MAX-ACCESS  read-only 
STATUS      current  
DESCRIPTION  
"<Definition> Indicates the number of octets (i.e., bytes) available within 
non-volatile, changeable memory. For CMS and BOS, this number shall be zero 
(0).
<Informative> See the Specifications in association with Requirement 3.6.7.2 
to determine the total memory that must be provided. This value only 
indicates the free changeable memory available to the SNMP context for this 
sign (i.e., it may be different than what is available to the entire field 
device).
<Parameter Type> Status
<Object Identifier> 1.3.6.1.4.1.1206.4.2.3.5.4"
::= { dmsMessage 4 }

-- 5.6.5	Number of Volatile Messages Parameter 
dmsNumVolatileMsg  OBJECT-TYPE 
SYNTAX      Integer32 (0..65535)
UNITS       "messages" 
MAX-ACCESS  read-only 
STATUS      current  
DESCRIPTION  
"<Definition> Indicates the current number of valid Messages stored in 
volatile, changeable memory. For CMS and BOS, this number shall be zero (0).
<Parameter Type> Status
<Object Identifier> 1.3.6.1.4.1.1206.4.2.3.5.5"
::= { dmsMessage 5 }

-- 5.6.6	Maximum Number of Volatile Messages Parameter 
dmsMaxVolatileMsg  OBJECT-TYPE 
SYNTAX      Integer32 (0..65535)
UNITS       "messages" 
MAX-ACCESS  read-only 
STATUS      current  
DESCRIPTION  
"<Definition> Indicates the maximum number of Messages that the sign can 
store in volatile, changeable memory. For CMS and BOS, this number shall be 
zero (0).
<Informative> See the Specifications in association with Requirement 3.6.7.3 
to determine the messages that must be supported.
<Parameter Type> Status
<Object Identifier> 1.3.6.1.4.1.1206.4.2.3.5.6"
::= { dmsMessage 6 }

-- 5.6.7	Free Bytes within Volatile Memory Parameter 
dmsFreeVolatileMemory  OBJECT-TYPE 
SYNTAX      Integer32 (0..2147483647)
UNITS       "octets" 
MAX-ACCESS  read-only 
STATUS      current 
DESCRIPTION  
"<Definition> Indicates the number of octets (i.e., bytes) available within 
volatile, changeable memory. For CMS and BOS, this number shall be zero (0).
<Informative> See the Specifications in association with Requirement 3.6.7.3 
to determine the total memory that must be provided. This value only 
indicates the free volatile memory available to this DMS context (i.e., it 
may be different than what is available to the entire field device).
<Parameter Type> Status
<Object Identifier> 1.3.6.1.4.1.1206.4.2.3.5.7"
::= { dmsMessage 7 }

-- 5.6.8	Message Table Parameter 
dmsMessageTable  OBJECT-TYPE 
SYNTAX      SEQUENCE OF DmsMessageEntry
MAX-ACCESS  not-accessible
STATUS      current 
DESCRIPTION 
"<Definition> A table containing the information needed to activate a Message 
on a sign. The values of a columnar object (except the dmsMessageStatus) 
cannot be changed when the dmsMessageStatus-object of that particular row is 
any value other than 'modifying'.
<Table Type> static
<Object Identifier> 1.3.6.1.4.1.1206.4.2.3.5.8"
::= {dmsMessage 8}

dmsMessageEntry OBJECT-TYPE
SYNTAX      DmsMessageEntry
MAX-ACCESS  not-accessible
STATUS      current 
DESCRIPTION 
"<Definition> Parameters of the Message Table."
INDEX {dmsMessageMemoryType, dmsMessageNumber}
::= {dmsMessageTable 1}

DmsMessageEntry ::= SEQUENCE {
   dmsMessageMemoryType      INTEGER,
   dmsMessageNumber          Integer32,
   dmsMessageMultiString     MultiString,
   dmsMessageOwner           NtcipOwnerString,
   dmsMessageCRC             Integer32,
   dmsMessageBeacon          Integer32,
   dmsMessagePixelService    Integer32,
   dmsMessageRunTimePriority Integer32,
   dmsMessageStatus          INTEGER
   } 

-- 5.6.8.1	Message Memory Type Parameter 
dmsMessageMemoryType  OBJECT-TYPE 
SYNTAX      INTEGER {
                 other (1), -- deprecated
                 permanent (2),
                 changeable (3),
                 volatile (4),
                 currentBuffer (5),
                 schedule (6),
                 blank (7)} 
MAX-ACCESS  read-only 
STATUS      current  
DESCRIPTION  
"<Definition> Indicates the memory-type used to store a message. Also 
provides access to current message (currentBuffer) and currently scheduled 
message (schedule). The rows associated with the 'currentBuffer', 'schedule', 
and 'blank' message types cannot be written into, because these are either 
filled in by the controller (currentBuffer and schedule) or pre-defined and 
not modifiable (blank).

The definitions of the enumerated values are:
  other - any other type of memory type that is not listed within one of 
     the values below, refer to device manual;
  permanent - non-volatile and non-changeable;
  changeable - non-volatile and changeable;
  volatile - volatile and changeable;
  currentBuffer - contains the information regarding the currently
     displayed message (basically a copy of the message table row 
     contents of the message that was successfully activated).
     Only one entry in the table can have the 
     value of currentBuffer and the value of the dmsMessageNumber 
     object shall be one (1). The content of the 
     dmsMessageMultiString object shall be the currently displayed 
     message (including a scheduled message), not the content of a 
     failed message activation attempt;
  schedule - this entry contains information regarding the currently 
     scheduled message as determined by the time-base scheduler (if 
     present). Only one entry in the table can have the value of 
     'schedule' and the value of dmsMessageNumber for this entry 
     shall be 1. Displaying a message through this table row shall set
     the dmsMsgSourceMode object value to 'timebasedScheduler'.
     When no message is currently active based upon the schedule
     or if the schedule currently does not point to any message within
     the message table, the schedule entry shall contain a copy of
     dmsMessageMemoryType 7 (blank) with a dmsMessageNumber value of 1.
  blank - there shall be 255 (message numbers 1 through 255) 
     pre-defined, static rows with this message type. These rows are 
     defined so that message codes (e.g., objects with SYNTAX of 
     either MessageIDCode or MessageActivationCodeV4) can blank the 
     sign at a stated run-time priority. The run-time priority of the blank 
     message is equal to the message number (e.g., blank message 
     number 1 has a run time priority of 1 and so on). The 
     dmsMessageCRC for all messages of this type shall be 0x0000 and 
     the dmsMessageMultiString shall be an OCTET STRING with a length of 
     zero (0). The activation priority shall be determined from the 
     activation priority of the MessageActivationCodeV4. 

<Informative> In v02, the enumerated value of 'other' was retired to improve 
interoperability.
<Parameter Type> Status
<Object Identifier> 1.3.6.1.4.1.1206.4.2.3.5.8.1.1"
::= { dmsMessageEntry 1 }

-- 5.6.8.2	Message Number Parameter 
dmsMessageNumber  OBJECT-TYPE 
SYNTAX      Integer32 (1..65535) 
MAX-ACCESS  read-only 
STATUS      current  
DESCRIPTION  
"<Definition> Enumerated listing of row entries within the value of the 
primary index to this table (dmsMessageMemoryType -object). When the primary 
index is 'currentBuffer' or 'schedule', then this value must be one (1). When 
the primary index is 'blank', this value shall be from 1 through 255 and all 
compliant devices must support all 255 of these 'blank' rows.
<Parameter Type> Status
<Object Identifier> 1.3.6.1.4.1.1206.4.2.3.5.8.1.2"
::= { dmsMessageEntry 2 }

-- 5.6.8.3	Message MULTI String Parameter 
dmsMessageMultiString  OBJECT-TYPE 
SYNTAX      MultiString  
MAX-ACCESS  read-write 
STATUS      current  
DESCRIPTION  
"<Definition> Contains the message in the format defined by the MultiString 
textual convention. 

When the primary index is 'schedule', 'blank', 'currentBuffer' or 
'permanent', this object shall return a notWritable error to any SET-request. 
When the primary index is 'schedule', the object shall return the MULTI 
string of the currently scheduled message in response to a GET-request 
(regardless whether this message is actually being displayed). 
<Parameter Type> Configuration
<Object Identifier> 1.3.6.1.4.1.1206.4.2.3.5.8.1.3"
::= { dmsMessageEntry 3 }

-- 5.6.8.4	Message Owner Parameter 
dmsMessageOwner  OBJECT-TYPE 
SYNTAX      NtcipOwnerString 
MAX-ACCESS  read-write 
STATUS      current  
DESCRIPTION  
"<Definition> Indicates the owner or author of this row.
<Informative> Prior to NTCIP 1203 v04, this object was restricted to NVT 
ASCII. Implementations can restrict which character values are supported.
<Parameter Type> Configuration
<Object Identifier> 1.3.6.1.4.1.1206.4.2.3.5.8.1.4"
::= { dmsMessageEntry 4 }

-- 5.6.8.5	Message CRC Parameter 
dmsMessageCRC  OBJECT-TYPE 
SYNTAX      Integer32 (0..65535) 
MAX-ACCESS  read-only 
STATUS      current  
DESCRIPTION  
"<Definition> Indicates the CRC-16 (polynomial defined in ISO/IEC 3309) value 
created using the values of the dmsMessageMultiString (MULTI-Message), the 
dmsMessageBeacon, and the dmsMessagePixelService objects in the order listed, 
not including the OER type or length fields. For messages of the 'blank' 
message type, the above algorithm shall be ignored and the dmsMessageCRC 
value shall always be zero (0). For messages of the 'schedule' message type, 
the CRC value of the currently scheduled message shall always be returned 
(regardless whether this message is actually being displayed).
<Informative> Prior to NTCIP 1203 v04, dmsMessageBeacon and 
dmsMessagePixelService could be interpretted as being optional to support. In 
this case, the calculated CRC assumed the value zero for the missing data. 
Starting with v04, all implementations are required to support these objects, 
even if they do not support the related functionality.
<Parameter Type> Status
<Object Identifier> 1.3.6.1.4.1.1206.4.2.3.5.8.1.5"
::= { dmsMessageEntry 5 }

-- 5.6.8.6	Message Beacon Parameter 
dmsMessageBeacon  OBJECT-TYPE 
SYNTAX      Integer32(0..255)  
MAX-ACCESS  read-write 
STATUS      current  
DESCRIPTION  
"<Definition> Indicates the dmsBeaconPlanIndex of the dmsBeaconPlanEntry to 
be used to control physical beacons during the display of the message. A 
value of zero (0) shall disable the beacons. Implementations that do not 
support physical beacons shall support this object but restrict its range to 
zero (0).
When the primary index is 'schedule', 'blank', 'currentBuffer', or 
'permanent', this object shall return a inconsistentValue error to any SET-
request. 
When the primary index is 'schedule', the object shall return the 
dmsMessageBeacon setting of the currently scheduled message in response to a 
GET-request (regardless whether this message is actually being displayed). 
When the dmsMessageMemoryType is 'permanent', the object shall return the 
dmsMessageBeacon setting of the factory-preset value in response to a GET-
request.
<Parameter Type> Configuration
<Object Identifier> 1.3.6.1.4.1.1206.4.2.3.5.8.1.6"
DEFVAL  {0} 
::= { dmsMessageEntry 6 }

-- 5.6.8.7	Message Pixel Service Parameter 
dmsMessagePixelService  OBJECT-TYPE 
SYNTAX      Integer32 (0..1) 
MAX-ACCESS  read-write 
STATUS      current  
DESCRIPTION  
"<Definition> Indicates whether pixel service shall be enabled (1) or 
disabled (0) while this message is active. Implementations that do not 
support pixel service shall support this object but restrict its range to 
zero (0).
When the primary index is 'schedule', 'blank', 'currentBuffer', or 
'permanent', this object shall return a inconsistentValue error to any SET-
request. 
When the primary index is 'schedule', the object shall return the 
dmsMessagePixelService setting of the currently scheduled message in response 
to a GET-request (regardless whether this message is actually being 
displayed). 
When the primary index is 'permanent', the object shall return the 
dmsMessagePixelService setting of the factory-preset value in response to a 
GET-request.
<Parameter Type> Configuration
<Object Identifier> 1.3.6.1.4.1.1206.4.2.3.5.8.1.7"
DEFVAL  {0} 
::= { dmsMessageEntry 7 }

-- 5.6.8.8	Message Run Time Priority Parameter 
dmsMessageRunTimePriority  OBJECT-TYPE 
SYNTAX      Integer32 (1..255) 
MAX-ACCESS  read-write 
STATUS      current  
DESCRIPTION  
"<Definition> Indicates the run time priority assigned to a particular 
message. The value of 1 indicates the lowest level, the value of 255 
indicates the highest level. When the dmsMessageMemoryType is 'schedule,' the 
value set in this object (e.g. dmsMessageRunTimePriority.6.1) shall override 
the run-time priority of the scheduled message. When the dmsMessageMemoryType 
is 'blank', the value returned shall be equal to the dmsMessageNumber of that 
particular message.
<Parameter Type> Configuration
<Object Identifier> 1.3.6.1.4.1.1206.4.2.3.5.8.1.8"
::= { dmsMessageEntry 8 }

-- 5.6.8.9	Message Status Parameter 
dmsMessageStatus  OBJECT-TYPE 
SYNTAX      INTEGER {
                 notUsed (1),
                 modifying (2),
                 validating (3),
                 valid (4),
                 error (5),
                 modifyReq (6),
                 validateReq (7),
                 notUsedReq (8) } 
MAX-ACCESS  read-write 
STATUS      current  
DESCRIPTION  
"<Definition> Indicates the current state of the message. This state-machine 
allows for defining a message, validating a message, and deleting a message. 
See Section 4.3.4 for additional details regarding the state-machine.
<Parameter Type> Configuration
<Object Identifier> 1.3.6.1.4.1.1206.4.2.3.5.8.1.9"
::= { dmsMessageEntry 9 }

-- 5.6.9	Validate Message Error Parameter 
dmsValidateMessageError  OBJECT-TYPE 
SYNTAX      INTEGER {
                 other (1),
                 none (2),
                 beacons (3),
                 pixelService (4),
                 syntaxMULTI (5) } 
MAX-ACCESS  read-only 
STATUS      current  
DESCRIPTION  
"<Definition> This is an error code used to identify why a message was not 
validated. If multiple errors occur, only the first value is indicated. The 
syntaxMULTI error is further detailed in the dmsMultiSyntaxError, 
dmsMultiSyntaxErrorPosition and dmsMultiOtherErrorDescription objects.
<Parameter Type> Status
<Object Identifier> 1.3.6.1.4.1.1206.4.2.3.5.9"
::= { dmsMessage 9 }

-- 5.7	Sign Control Objects 
signControl  OBJECT-IDENTITY 
STATUS  current 
DESCRIPTION
"<Definition> This node is an identifier used to group all objects for 
support of DMS sign control functions that are common to DMS devices. 
<Object Identifier> 1.3.6.1.4.1.1206.4.2.3.6"
::= { dms 6 }


-- 5.7.1	Control Mode Parameter 
dmsControlMode  OBJECT-TYPE 
SYNTAX      INTEGER {
                 other (1),        -- deprecated
                 local (2),
                 external (3),     -- obsolete
                 central (4),
                 centralOverride (5),
                 simulation (6)    -- obsolete 
                 } 
MAX-ACCESS  read-write 
STATUS      current  
DESCRIPTION  
"<Definition> A value indicating the mode that is currently controlling the 
sign.
<Format>
The possible modes are:
  other - (deprecated) Other control mode supported by the device (refer to 
device manual);
  local - Local control mode (control is at DMS controller);
  external - (obsolete) External control mode; 
  central - Central control mode;
  centralOverride - Central station took control over 'local' control, even 
     though the control switch at the sign was set to 'local';
  simulation  - (obsolete) controller is in a mode where it accepts every 
     command and it pretends that it would execute them but this does not 
     happen because the controller only simulates.
<Informative> In v02, the enumerated values of 'other', 'external', and 
'simulation' were deprecated to improve interoperability. the values of 
external and simulation were never widely used and made obsolete in v04.
<Parameter Type> Configuration
<Object Identifier> 1.3.6.1.4.1.1206.4.2.3.6.1"
DEFVAL  {central} 
::= { signControl 1 }

-- 5.7.2	Software Reset Parameter 
dmsSWReset  OBJECT-TYPE 
SYNTAX      Integer32 (0..1) 
MAX-ACCESS  read-write 
STATUS      deprecated  
DESCRIPTION  
"<Definition> A software interface to initiate a controller reset. The 
execution of the controller reset shall set this object to the value 0. 
Setting this object to a value of 1 causes the controller to reset. 
<Format> Defined values are 
zero (0) = no reset, 
one (1) = reset.
<Superseded by> ISO26048-1-Controller:fdControllerReset
<Informative> This object was deprecated in NTCIP 1203 v04 in favor of the 
more generic object defined in ISO 26048-1.
<Parameter Type> Control
<Object Identifier> 1.3.6.1.4.1.1206.4.2.3.6.2"
DEFVAL  {0} 
::= { signControl 2 }

-- 5.7.3	Activate Message Parameter 
dmsActivateMessage  OBJECT-TYPE 
SYNTAX      MessageActivationCode 
MAX-ACCESS  read-write 
STATUS      deprecated  
DESCRIPTION  
"<Definition> A code indicating the active message. The value of this object 
may be SET by a management station or modified by logic internal to the DMS 
(e.g., activation of the end duration message, etc.). 

When modified by internal logic with a reference to a message ID code, the 
duration indicates 65535 (infinite), the activate priority indicates 255, and 
the source address indicates an address of 127.0.0.1.

If a GET is performed on this object, the DMS shall respond with the value 
for the last message that was successfully activated.
The dmsActivateMsgError object shall be updated appropriately upon any 
attempt to update the value of this object, whether from an internal or 
external source.

If a message activation error occurs (e.g., dmsActivateMsgError is updated to 
a value other than 'none'), the new message shall not be activated and, if 
the activation request originated from a SET request, a genErr shall be 
returned. A management station should then GET the dmsActivateMsgError object 
as soon as possible to minimize the chance of additional activation attempts 
from overwriting the dmsActivateMsgError.

If a message is attempted to be activated via the scheduler or any internal 
message (e.g., end duration message, etc.) and the message to be activated 
contains an error, than the following objects shall be set to the appropriate 
values (as defined within these objects):
- dmsActivateMsgError,
- dmsActivateErrorMsgCode,
- dmsMultiSyntaxError,
- dmsMultiSyntaxErrorPosition (if supported),
- dmsMultiOtherErrorDescription (if supported),
- dmsDrumStatus (if supported)

A 'criticalTemperature' alarm shall have no effect on the 'activation' of a 
message, it will only affect the display of the active message. Thus, a 
message activation may occur during a 'criticalTemperature' alarm and the 
sign controller will behave as if the message is displayed. However, the 
shortErrorStatus will indicate a criticalTemperature alarm and the sign face 
illumination will be off. As soon as the DMS determines that the 
'criticalTemperature' alarm is no longer present, the DMS shall display the 
message stored in the currentBuffer. 

<Superseded by> dmsActivateMessageV4  
<Informative> This object was deprecated in NTCIP 1203 v04 in favor of 
MessageActivationCodeV4, which is designed to support IPv6 and to more 
securely record the source of the request.
<Parameter Type> Control
<Object Identifier> 1.3.6.1.4.1.1206.4.2.3.6.3"
::= { signControl 3 }

-- 5.7.4	Message Display Time Remaining Parameter 
dmsMessageTimeRemaining  OBJECT-TYPE 
SYNTAX      Integer32 (0..65535)
UNITS       "minutes" 
MAX-ACCESS  read-write 
STATUS      current  
DESCRIPTION  
"<Definition> Indicates the amount of remaining time in minutes that the 
current message shall be active. The time shall be accurate to the nearest 
second and rounded up to the next full minute. For example, a value of 2 
shall indicate that the time remaining is between 1 minute and 0.1 seconds 
and 2 minutes. 
When a new message is activated with a minute-based duration, or this object 
is directly SET, the minute-based duration value shall be multiplied by 60 to 
determine the number of seconds that the message shall be active. Thus, if a 
message activation is for 2 minutes, the DMS will be assured to display the 
message for 120 seconds.
The value 65535 indicates an infinite duration. A value of zero (0) shall 
indicate that the current message display duration has expired.

A SET operation on this object shall allow a Central Computer to extend or 
shorten the duration of the message. Setting this object to zero (0) shall 
result in the immediate display of the dmsEndDurationMessage.
<Parameter Type> Control
<Object Identifier> 1.3.6.1.4.1.1206.4.2.3.6.4"
DEFVAL  {65535} 
::= { signControl 4 }

-- 5.7.5	Message Table Source Parameter 
dmsMsgTableSource  OBJECT-TYPE 
SYNTAX      MessageIDCode 
MAX-ACCESS  read-only 
STATUS      current  
DESCRIPTION  
"<Definition> Identifies the message number used to generate the currently 
displayed message. This object is written to by the device when the new 
message is loaded into the currentBuffer of the dmsMessageTable. The value of 
this object contains the message ID code of the message that was copied into 
the 'currentBuffer'. This value can only be of message type 'permanent', 
'volatile', 'changeable', or 'blank'. 
<Parameter Type> Status
<Object Identifier> 1.3.6.1.4.1.1206.4.2.3.6.5"
::= { signControl 5 }

-- 5.7.6	Message Requester ID Parameter 
dmsMsgRequesterID  OBJECT-TYPE 
SYNTAX      IpAddress 
MAX-ACCESS  read-only 
STATUS      deprecated 
DESCRIPTION  
"<Definition> A copy of the source-address field from the dmsActivateMessage-
object used to activate the current message. If the current message was not 
activated by the dmsActivateMessage-object, then the value of this object 
shall be zero (0).
<Superceded by> dmsMsgRequesterAddressType, dmsMsgRequesterAddress, and 
dmsMsgRequesterSecurityName
<Informative> This object was deprecated in v04 to more accurately and 
securely capture the source of the request.
<Parameter Type> Status
<Object Identifier> 1.3.6.1.4.1.1206.4.2.3.6.6"
REFERENCE  "RFC 1155, May 1990" 
::= { signControl 6 }

-- 5.7.7	Message Source Mode Parameter 
dmsMsgSourceMode  OBJECT-TYPE 
SYNTAX      INTEGER {
                 other (1),
                 local (2),
                 external (3),
                 otherCom1( 4), -- obsolete
                 otherCom2 (5), -- obsolete
                 otherCom3 (6), -- obsolete
                 otherCom4 (7), -- obsolete
                 central (8),
                 timebasedScheduler (9),
                 powerRecovery (10),
                 reset (11),
                 commLoss (12),
                 powerLoss (13),
                 endDuration (14)
                 } 
MAX-ACCESS  read-only 
STATUS      current  
DESCRIPTION  
"<Definition> Indicates the source that initiated the currently displayed 
message. 
<Format> The enumerations are defined as:
  other (1) - the currently displayed message was activated based on a 
     condition other than the ones defined below. This would include any
     auxiliary devices.
  local (2) - the currently displayed message was activated at the sign 
     controller using either an onboard terminal or a local interface.
  external (3) - the currently displayed message was activated from a locally 
    connected device using serial (or other type of) connection to the sign 
    controller such as a laptop or a PDA. This mode shall only be used, if 
    the sign controller is capable of distinguishing between a local input 
    (see definition of 'local (2)') and a serial connection.
  central (8) - the currently displayed message was activated from the 
    central computer.
  timebasedScheduler (9) - the currently displayed message was activated from 
    the timebased scheduler as configured within the sign controller.
  powerRecovery (10) - the currently displayed message was activated based 
    on the settings within the dmsLongPowerRecoveryMessage, 
    dmsShortPowerRecoveryMessage, and the dmsShortPowerLossTime objects.
  reset (11) - the currently displayed message was activated based on the 
    settings within the dmsResetMessage object.
  commLoss (12) - the currently displayed message was activated based on 
    the settings within the dmsCommunicationsLossMessage object.
  powerLoss (13) - the currently displayed message was activated based on 
    the settings within the dmsPowerLossMessage object. Note: it may not be 
    possible to point to this message depending on the technology, e.g. it 
    may not be possible to display a message on pure LED or fiber-optic signs 
    DURING power loss.
  endDuration (14) - the currently displayed message was activated based on 
    the settings within the dmsEndDurationMessage object.

<Informative> In v02, the enumerated values of 'otherComX' were deprecated to 
improve interoperability.
<Parameter Type> Status
<Object Identifier> 1.3.6.1.4.1.1206.4.2.3.6.7"
::= { signControl 7 }

-- 5.7.8	Short Power Loss Recovery Message Parameter 
dmsShortPowerRecoveryMessage  OBJECT-TYPE 
SYNTAX      MessageIDCode 
MAX-ACCESS  read-write 
STATUS      current  
DESCRIPTION  
"<Definition> Indicates the message that shall be activated after a power 
recovery following a short power loss affecting the device. Specifying the 
dmsMessageMemoryType of 'currentBuffer', dmsMessageNumber of 1 and 
dmsMessageCRC of 0 indicates that the message displayed prior to the power 
loss will be reactivated after the power recovery using the 'activate' MULTI-
default settings from before the power loss. The message shall be activated 
with: 
- a duration of 65535 (infinite), unless the message type is 'currentBuffer'. 
In the latter case, the duration is determined by the value of the 
dmsMessageTimeRemaining object (at the time of the power loss) minus the 
power outage time; 
- an activation priority of 255.
Upon activation of the message, the run-time priority value shall be obtained 
from the message table row specified by this object. 
The length of time that defines a short power loss is indicated in the 
dmsShortPowerLossTime-object.
<Informative> The default value indicates a messageMemoryType of 7 (blank), a 
messageNumber of 1, and a messageCRC 0f 0x0000
<Parameter Type> Configuration
<Object Identifier> 1.3.6.1.4.1.1206.4.2.3.6.8"
DEFVAL { '0700010000'H }
::= { signControl 8 }

-- 5.7.9	Long Power Loss Recovery Message Parameter 
dmsLongPowerRecoveryMessage  OBJECT-TYPE 
SYNTAX      MessageIDCode 
MAX-ACCESS  read-write 
STATUS      current  
DESCRIPTION  
"<Definition> Indicates the message that shall be activated after a power 
recovery following a long power loss affecting the device. Specifying the 
dmsMessageMemoryType of 'currentBuffer', dmsMessageNumber of 1 and 
dmsMessageCRC of 0 indicates that the message displayed prior to the power 
loss will be reactivated after the power recovery using the 'activate' MULTI-
default settings from before the power loss. The message shall be activated 
with
- a duration of 65535 (infinite), (if this object points to a value of 
'currentBuffer', the duration is determined by the value of the 
dmsMessageTimeRemaining object minus the power outage time)
- an activation priority of 255. 
Upon activation of the message, the run-time priority value shall be obtained 
from the message table row specified by this object.
The length of time that defines a long power loss is indicated in the 
dmsShortPowerLossTime-object.
<Parameter Type> Configuration
<Object Identifier> 1.3.6.1.4.1.1206.4.2.3.6.9"
DEFVAL { '0700010000'H }
::= { signControl 9 }

-- 5.7.10	Short Power Loss Time Definition Parameter 
dmsShortPowerLossTime  OBJECT-TYPE 
SYNTAX      Integer32 (0..65535)
UNITS       "seconds" 
MAX-ACCESS  read-write 
STATUS      current  
DESCRIPTION  
"<Definition> Indicates the time, in seconds, from the start of power loss to 
the threshold where a short power loss becomes a long power loss. If the 
value is set to zero (0), all power failures are defined as long power 
losses.
<Parameter Type> Configuration
<Object Identifier> 1.3.6.1.4.1.1206.4.2.3.6.10"
DEFVAL { 0 }
::= { signControl 10 }

-- 5.7.11	Reset Message Parameter 
dmsResetMessage  OBJECT-TYPE 
SYNTAX      MessageIDCode 
MAX-ACCESS  read-write 
STATUS      current  
DESCRIPTION  
"<Definition> Indicates the message that shall be activated after a Reset 
(either software or hardware) of the device. This includes all resets other 
than those due to power recovery assuming that the device can differentiate 
between a reset and a power recovery event. Specifying the 
dmsMessageMemoryType of 'currentBuffer', dmsMessageNumber of 1 and 
dmsMessageCRC of 0 indicates that the message displayed prior to the reset 
will be reactivated after the reset using the 'activate' MULTI-default 
settings from before the reset. The message shall be activated with
- a duration of 65535 (infinite) (if this object points to a value of 
'currentBuffer', the duration is determined by the value of the 
dmsMessageTimeRemaining object minus the power outage time); 
- an activation priority of 255.
Upon activation of the message, the run-time priority value shall be obtained 
from the message table row specified by this object. 
<Parameter Type> Configuration
<Object Identifier> 1.3.6.1.4.1.1206.4.2.3.6.11"
DEFVAL { '0700010000'H }
::= { signControl 11 }

-- 5.7.12	Communications Loss Message Parameter 
dmsCommunicationsLossMessage  OBJECT-TYPE 
SYNTAX      MessageIDCode 
MAX-ACCESS  read-write 
STATUS      current  
DESCRIPTION  
"<Definition> Indicates the message that shall be activated when the time 
since the last communications from a management station exceeds the 
dmsTimeCommLoss time. The message shall be activated with
- a duration of 65535 (infinite) (if this object points to a value of 
'currentBuffer', the duration is determined by the value of the 
dmsMessageTimeRemaining object); 
- an activation priority of 255. 
If the value referenced by this object is invalid, the sign will display a 
blank message. 
Upon activation of the message, the run-time priority value shall be obtained 
from the message table row specified by this object. 
The value of this object shall not be implemented when the value of the 
dmsControlMode is set to 2 (local). Once the value of the dmsControl Mode 
object is set to 4 (central) or 5 (centralOverride) and the value of the 
dmsTimeCommLoss parameter has been reached, the value of this object shall be 
implemented.
<Parameter Type> Configuration
<Object Identifier> 1.3.6.1.4.1.1206.4.2.3.6.12"
DEFVAL { '0700010000'H }
::= { signControl 12 }

-- 5.7.13	Communication Loss Time Definition Parameter 
dmsTimeCommLoss  OBJECT-TYPE 
SYNTAX      Integer32 (0..65535)
UNITS       "minutes" 
MAX-ACCESS  read-write 
STATUS      current  
DESCRIPTION  
"<Definition> Defines the maximum time (inclusive), in minutes, between 
successive Application Layer messages that can occur before a communication 
loss is assumed. If this object is set to zero (0), communications loss shall 
be ignored.

The countdown timer associated with this parameter shall be suspended while 
the sign control parameter has a value of 'local (2)', e.g., the sign is in 
local control. The countdown timer shall be restarted (reset and started 
again) once the sign control parameter value is switched to 'central (4)' or 
'centralOverride (5)'.
<Informative> This timer differs from the Data Link Layer timers (T1 to T4). 
A dial-up circuit may have short time-outs at the DL Layer, but central might 
only dial up once a month to confirm operation, in which case this object 
would be set to ~ 35 days.
<Parameter Type> Configuration
<Object Identifier> 1.3.6.1.4.1.1206.4.2.3.6.13"::= { signControl 13 }

-- 5.7.14	Power Loss Message Parameter 
dmsPowerLossMessage  OBJECT-TYPE 
SYNTAX      MessageIDCode 
MAX-ACCESS  read-write 
STATUS      current  
DESCRIPTION  
"<Definition> Indicates the message that shall be activated DURING the loss 
of power of the device. The message shall be activated with:
a duration of 65535 (infinite) (if this object points to a value of 
'currentBuffer', the duration is determined by the value of the 
dmsMessageTimeRemaining object); 
an activation priority of 255.
Upon activation of the message, the run-time priority value shall be obtained 
from the message table row specified by this object. 

<Informative> Not all technologies support the means to display a message 
while the power is off.
<Parameter Type> Configuration
<Object Identifier> 1.3.6.1.4.1.1206.4.2.3.6.14"
DEFVAL { '0700010000'H }
::= { signControl 14 }

-- 5.7.15	End Duration Message Parameter 
dmsEndDurationMessage  OBJECT-TYPE 
SYNTAX      MessageIDCode 
MAX-ACCESS  read-write 
STATUS      current  
DESCRIPTION  
"<Definition> Indicates the message that shall be activated after the 
indicated duration for a message has expired and no other Message had been 
activated (see dmsActivateMessage). The message shall be activated with
- a duration of 65535 (infinite) (if this object points to a value of 
'currentBuffer', the duration is determined by the value of the 
dmsMessageTimeRemaining object); 
- an activation priority of 255.
Upon activation of the message, the run-time priority value shall be obtained 
from the message table row specified by this object. 

If the end duration message does not activate because this object is an 
invalid value, the sign shall blank with the default value of this object.

<Parameter Type> Configuration
<Object Identifier> 1.3.6.1.4.1.1206.4.2.3.6.15"
DEFVAL { '0700010000'H }
::= { signControl 15 }

-- 5.7.16	Memory Management Parameter 
dmsMemoryMgmt  OBJECT-TYPE 
SYNTAX      INTEGER  {
                 other (1), -- deprecated 
                 normal (2),
                 clearChangeableMessages (3),
                 clearVolatileMessages (4) } 
MAX-ACCESS  read-write 
STATUS      current  
DESCRIPTION  
"<Definition> Allows the system to manage the device's memory. 

<Format>
SNMP Get operations on this object should always return normal (2).

   clearChangeableMessages (3): the controller shall set dmsMessageStatus for 
all changeable messages to notUsed (1), and release all memory associated 
with changeable messages.  This action does not affect any changeable 
graphics or fonts.

   clearVolatileMessages (4): the controller shall set dmsMessageStatus for 
all volatile messages to notUsed (1), and release all memory associated with 
volatile messages.  This action does not affect any changeable graphics or 
fonts.

<Informative> In v02, the enumerated value of 'other' was deprecated to 
improve interoperability.

<Parameter Type> Control
<Object Identifier> 1.3.6.1.4.1.1206.4.2.3.6.16"
DEFVAL  {normal} 
::= { signControl 16 }

-- 5.7.17	Activate Message Error Parameter 
dmsActivateMsgError  OBJECT-TYPE 
SYNTAX      INTEGER {
                 other (1),
                 none (2),
                 priority (3),
                 messageStatus (4),
                 messageMemoryType (5),
                 messageNumber (6),
                 messageCRC (7),
                 syntaxMULTI (8),
                 localMode (9),
                 centralMode (10),
                 centralOverrideMode (11),
                 defaultFont (12),
                 beaconPlan (13) } 
MAX-ACCESS  read-only 
STATUS      current  
DESCRIPTION  
"<Definition> This is an error code used to identify why a message was not 
displayed. Even if multiple errors occur, only one error is indicated.
<Format>
  other (1):  any error not defined below.
  none (2): no error.
  priority(3):  the activation priority in the MessageActivationCodeV4 is
     less than the run time priority of the  currently displayed message.
     If this error occurs, the corresponding bit (message error) within 
     the 'shortErrorStatus' object shall be set. 
  messageStatus(4):  the 'dmsMessageStatus' of the message to be 
     activated is not 'valid'. If this error  occurs, the corresponding bit 
     (message error) within the 'shortErrorStatus' object shall be set.
     Note: In the 1997 version of NTCIP 1203, this bit was assigned 
     the name of 'underValidation'. It has been renamed to better 
     reflect the fact that this bit can be set due to the message being 
     in a number of different states, not just the 'validating' state.
  messageMemoryType(5):  the message memory type in the 
     MessageActivationCodeV4 is not supported by the  device. If this 
     error occurs, the corresponding bit (message error) within the 
     'shortErrorStatus' object shall be set. 
  messageNumber(6):  the message number in the 
     MessageActivationCodeV4 is not supported or is not defined 
     (populated) by the device. If this error occurs, the corresponding 
     bit (message error) within the 'shortErrorStatus' object shall be set.
  messageCRC(7):  the checksum in the MessageActivationCodeV4 is 
     different than the CRC value  contained in the 'dmsMessageCRC'. 
     If this error occurs, the corresponding bit (message error) within  
     the 'shortErrorStatus' object shall be set.
  syntaxMULTI(8):  a MULTI syntax error was detected during 
     message activation. The error is further detailed in the 
     'dmsMultiSyntaxError', 'dmsMultiSyntaxErrorPosition', and 
     'dmsMultiOtherErrorDescription' objects. If this error occurs, the 
     corresponding bit (message error) within the 'shortErrorStatus' object 
     shall be set.
  localMode(9):  the central system attempted to activate a message 
     while the 'dmsControlMode' object is  'local'. This error shall NOT 
     be set if the value of the 'dmsControlMode' is set to 
     'central',  or 'centralOverride'. If this error occurs, the 
     corresponding bit (message error) within the 'shortErrorStatus' 
     object shall be set.
  centralMode (10):  a locally connected system attempted to activate 
     a message while the 'dmsControlMode' object is 'central'. 
     This error shall NOT be set if the value of the 'dmsControlMode'
     is set to 'local'. If this error occurs, the corresponding
     bit (message error) within the 'shortErrorStatus' 
     object shall be set. 
  centralOverrideMode (11):  a locally connected system attempted to activate 
     a message while the 'dmsControlMode' object is 'centralOverride', even 
     though the local switch is set to local control. 
     If this error occurs, the corresponding bit (message error)
     within the 'shortErrorStatus' object shall be set.
  defaultFont (12): The font referenced by defaultFont has a fontStatus 
     other than readyForUse or inUse.
  beaconPlan (13): The beacon plan referenced by dmsMessageBeacon has a 
dmsBeaconPlanRowStatus other than active.

A 'criticalTemperature' alarm shall have no effect on the 'activation' of a 
message, it only effects the display of the active message. Thus, a message 
activation may occur during a 'criticalTemperature' alarm and the sign 
controller behaves as if the message is displayed. However, the 
shortErrorStatus indicates a criticalTemperature alarm and the sign face 
illumination is off. As soon as the DMS determines that the 
'criticalTemperature' alarm is no longer present, the DMS shall display the 
message stored in the currentBuffer.
<Parameter Type> Status
<Object Identifier> 1.3.6.1.4.1.1206.4.2.3.6.17"
::= { signControl 17 }

-- 5.7.18	MULTI Syntax Error Parameter 
dmsMultiSyntaxError  OBJECT-TYPE 
SYNTAX      INTEGER {
                 other (1),
                 none (2),
                 unsupportedTag (3),
                 unsupportedTagValue (4),
                 textTooBig (5),
                 fontNotDefined (6),
                 characterNotDefined (7),
                 fieldDeviceNotExist (8),
                 fieldDeviceError (9),
                 flashRegionError (10),
                 tagConflict (11),
                 tooManyPages (12),
                 fontVersionID (13),
                 graphicID (14),
                 graphicNotDefined (15),
                 invalidCharacterEncoding (16) } 
MAX-ACCESS  read-only 
STATUS      current  
DESCRIPTION  
"<Definition> This is an error code used to identify the first detected 
syntax error within the MULTI message.
<Format>
  other (1):  An error other than one of those listed.
  none (2):  No error detected.
  unsupportedTag (3):  The tag is not supported by this device.
  unsupportedTagValue (4):  The tag value is not supported by this 
     device.
  textTooBig (5):  Too many characters on a line, too many lines for a
     page, or font is too large for the display.
  fontNotDefined (6):  The font is not defined in this device.
  characterNotDefined (7):  The character is not defined in the 
     selected font.
  fieldDeviceNotExist (8):  The field device does not exist / is not
     connected to this device.
  fieldDeviceError (9):  This device is not receiving input from the
     referenced field device and/or the field device has a  fault.
  flashRegionError (10):  The flashing region cannot be flashed by this
     device.
  tagConflict (11):  The message cannot be displayed with the
     combination of tags and/or tag implementation cannot be resolved.
  tooManyPages (12):  Too many pages of text exists in the message.
  fontVersionID (13):  The fontVersionID contained in the MULTI tag
     [fox,cccc] does not match the fontVersionID for the fontNumber 
     Indicated (or the font is not ready making the fontVersionID 
     invalid).
  graphicID (14):  The dmsGraphicID contained in the 
     MULTI tag [gx,cccc] does not match the dmsGraphicID for the
     dmsGraphicIndex indicated (or the graphic is not ready making the 
     dmsGraphicID invalid).
  graphicNotDefined (15):  The graphic is not defined in this device.
  invalidCharacterEncoding (16): The encoding of a character cannot be 
     decoded according to the current defaultCharacterSet. 
<Informative> Within eightBit encoding, all encodings are valid except for 
0x00; implementations may report 'characterNotDefined' for this situation to 
support backwards compatibility but invalidCharacterEncoding is preferred. 
Within utf8Style encoding, there are many encodings that are invalid (e.g., 
any octet with all four high-order bits set is invalid).
<Parameter Type> Status
<Object Identifier> 1.3.6.1.4.1.1206.4.2.3.6.18"
::= { signControl 18 }

-- 5.7.19	Position of MULTI Syntax Error Parameter 
dmsMultiSyntaxErrorPosition  OBJECT-TYPE 
SYNTAX      Integer32 (0..65535)
UNITS       "characters" 
MAX-ACCESS  read-only 
STATUS      current  
DESCRIPTION  
"<Definition> This is the offset from the first character (e.g. first 
character has offset 0, second is 1, etc.) of the MULTI string where the 
SYNTAX error occurred.
<Informative>The offset is measured in characters, which can be different 
than the number of octets when defaultCharacterSet has a value of utf8Style.
<Parameter Type> Status
<Object Identifier> 1.3.6.1.4.1.1206.4.2.3.6.19"
::= { signControl 19 }

-- 5.7.20	Other MULTI Error Parameter 
dmsMultiOtherErrorDescription  OBJECT-TYPE 
SYNTAX      SnmpAdminString (SIZE (0..50)) 
MAX-ACCESS  read-only 
STATUS      current  
DESCRIPTION  
"<Definition> Indicates vendor-specified error message descriptions. 
Associated errors occurred due to vendor-specific MULTI-tag responses. The 
value of this object is valid only if dmsValidateMessageError has a value of 
'syntaxMULTI(5)' or dmsActivateMsgError has a value of 'syntaxMULTI(8)' and 
dmsMultiSyntaxError is 'other(1)'. The language used for this text-based 
message shall be as defined by ISO26048-1-Controller:fdDefaultLanguage.
<Informative> Prior to NTCIP 1203 v04, this object type only supported NVT-
ASCII characters. 
<Parameter Type> Status
<Object Identifier> 1.3.6.1.4.1.1206.4.2.3.6.20"
::= { signControl 20 }

-- 5.7.21	Pixel Service Duration Parameter 
vmsPixelServiceDuration  OBJECT-TYPE 
SYNTAX      Integer32 (0..65535)
UNITS       "seconds" 
MAX-ACCESS  read-write 
STATUS      deprecated  
DESCRIPTION  
"<Definition> Indicates the number of seconds to perform pixel service on an 
entire sign. If the vmsPixelServiceDuration expires during a pixel service 
routine, that routine shall be completed before stopping or restarting a new 
pixel service routine due to vmsPixelServiceFrequency. A value of zero 
disables pixel service.
<Superseded by> vmsPixelServiceDurationV4
<Informative> This object was deprecated in NTCIP 1203 v04 to provide better 
and more appropriate resolution for the duration (i.e., ms rather than s)
<Parameter Type> Configuration
<Object Identifier> 1.3.6.1.4.1.1206.4.2.3.6.21"
::= { signControl 21 }

-- 5.7.22	Pixel Service Frequency Parameter 
vmsPixelServiceFrequency  OBJECT-TYPE 
SYNTAX      Integer32 (0..1440)
UNITS       "minutes" 
MAX-ACCESS  read-write 
STATUS      current  
DESCRIPTION  
"<Definition> Indicates the pixel service cycle time (period) in minutes. A 
value of zero indicates continuous pixel service from vmsPixelServiceTime to 
the epoch of midnight. A value of 1440 indicates one pixel service in a 24-
hour period.
<Parameter Type> Configuration
<Object Identifier> 1.3.6.1.4.1.1206.4.2.3.6.22"
DEFVAL  {1440} 
::= { signControl 22 }

-- 5.7.23	Pixel Service Time Parameter 
vmsPixelServiceTime  OBJECT-TYPE 
SYNTAX      Integer32 (0..1440)
UNITS       "minutes" 
MAX-ACCESS  read-write 
STATUS      current  
DESCRIPTION  
"<Definition> Indicates the base time at which the first pixel service shall 
occur. Time is expressed in minutes from the epoch of midnight of each day. 
Midnight shall be determined by local time, if the local clock feature (i.e., 
ISO 26048-1, 8.3.2) is supported; otherwise, it shall be based on UTC time.
<Parameter Type> Configuration
<Object Identifier> 1.3.6.1.4.1.1206.4.2.3.6.23"
DEFVAL  {1} 
::= { signControl 23 }

-- 5.7.24	Message Code of the Activation Error Parameter
dmsActivateErrorMsgCode  OBJECT-TYPE 
SYNTAX      MessageActivationCode 
MAX-ACCESS  read-only 
STATUS      deprecated  
DESCRIPTION  
"<Definition> Indicates the MessageActivationCode that resulted in the 
current value of the dmsActivateMsgError object.
<Superseded by> dmsActivateErrorMsgCodeV4
<Informative> This object was deprecated in NTCIP 1203 v04 to use the updated 
MessageActivationCodeV4
<Parameter Type> Status
<Object Identifier> 1.3.6.1.4.1.1206.4.2.3.6.24"
::= { signControl 24 }

-- 5.7.25	Activate Message State Parameter
dmsActivateMessageState  OBJECT-TYPE 
SYNTAX      INTEGER {
              fastActivationSign(1),
              slowActivatedOK(2),
              slowActivatedError(3),
              slowActivating(4) } 
MAX-ACCESS  read-only 
STATUS      current  
DESCRIPTION  
"<Definition> Signs that are able to reliably activate a message in less than 
the maximum response time should always return 'fastActivationSign(1)'. This 
allows a central to use this object to determine whether or not the sign does 
fast activation (that is, whether the sign can immediately change the 
display). Signs that may require more than the maximum response time to 
activate a message (such as a rotary drum sign) shall set this object to 
'slowActivating(4)' during the changing of the display and when the message 
change has completed shall change it to 'slowActivatedOK(2)' if successful or 
'slowActivatedError(3)' if an error occurred during the display change.

A sign with fast activation uses this object only to indicate that it is a 
fast activation sign. Such a sign provides an immediate response to a SET of 
dmsActivateMessageV4 (or dmsActivateMessage).

With a slow activation sign there are two opportunities to detect an error. 
The first comes when the SET of dmsActivateMessageV4 is performed, just as in 
the fast activation sign. It could be a bad message number or other error. If 
such an error is received, the message change does not occur and therefore 
this object can be ignored. If the SET of dmsActivateMessageV4 succeeds, then 
the central must wait for either slowActivatedOK or slowActivatedError in 
this object. If the sign detects an error, it shall set this object to 
slowActivatedError and set the 'message error' bit in the shortErrorStatus 
object. When a central receives slowActivatedError, it shall examine other 
status objects specific to the sign, such as the rotary drum status objects, 
to determine the precise error.
<Parameter Type> Status
<Object Identifier> 1.3.6.1.4.1.1206.4.2.3.6.25"
::= { signControl 25 }

-- 5.7.26	Activate Message V4 Parameter 
dmsActivateMessageV4  OBJECT-TYPE 
SYNTAX      MessageActivationCodeV4 
MAX-ACCESS  read-write 
STATUS      current  
DESCRIPTION  
"<Definition> A code indicating the active message or message to be 
activated. The value of this object may be SET by a management station or 
modified by logic internal to the DMS (e.g., activation of the end duration 
message, etc.). 

When modified by internal logic with a reference to a message ID code, the 
duration indicates 65535 (infinite) and the activate priority indicates 255.

If a GET is performed on this object, the DMS shall respond with the value 
for the last message that was successfully activated.

Upon any attempt to update the value of this object, whether from an internal 
or external source, the following objects shall be updated appropriately:
- dmsActivateMsgError,
- dmsActivateErrorMsgCodeV4,
- dmsMultiSyntaxError,
- dmsMultiSyntaxErrorPosition (if supported),
- dmsMultiOtherErrorDescription (if supported),
- dmsDrumStatus (if supported)

If a message activation error occurs (e.g., dmsActivateMsgError is updated to 
a value other than 'none'), the new message shall not be activated and, if 
the activation request originated from a SET request, the appropriate error 
code (NTCIP 1203 v04, Clause 4.3.5) shall be returned. A management station 
should then GET the dmsActivateMsgError object as soon as possible to 
minimize the chance of additional activation attempts from overwriting the 
dmsActivateMsgError.

A 'criticalTemperature' alarm shall have no effect on the 'activation' of a 
message, it will only affect the display of the active message. Thus, a 
message activation may occur during a 'criticalTemperature' alarm and the 
sign controller will behave as if the message is displayed. However, the 
shortErrorStatus will indicate a criticalTemperature alarm and the sign face 
illumination will be off. As soon as the DMS determines that the 
'criticalTemperature' alarm is no longer present, the DMS shall display the 
message stored in the currentBuffer. 
<Parameter Type> Control
<Object Identifier> 1.3.6.1.4.1.1206.4.2.3.6.26"
::= { signControl 26 }

-- 5.7.27	Message Code of the Activation Error V4 Parameter
dmsActivateErrorMsgCodeV4  OBJECT-TYPE 
SYNTAX      MessageActivationCodeV4 
MAX-ACCESS  read-only 
STATUS      current  
DESCRIPTION  
"<Definition> Indicates the MessageActivationCodeV4 that resulted in the 
current value of the dmsActivateMsgError object.
<Parameter Type> Status
<Object Identifier> 1.3.6.1.4.1.1206.4.2.3.6.27"
::= { signControl 27 }

-- 5.7.28	Message Requester Address Type Parameter 
dmsMsgRequesterAddressType  OBJECT-TYPE 
SYNTAX      TransportAddressType 
MAX-ACCESS  read-only 
STATUS      current 
DESCRIPTION  
"<Definition> An indication of the type of address used by the data packet 
that contained the request to activate the current message. If the current 
message was activated by internal logic (e.g., scheduling logic), the value 
of this object shall be local (13). 
<Parameter Type> Status
<Object Identifier> 1.3.6.1.4.1.1206.4.2.3.6.28"
REFERENCE  "RFC 3419, December 2002" 
::= { signControl 28 }

-- 5.7.29	Message Requester Address Parameter 
dmsMsgRequesterAddress  OBJECT-TYPE 
SYNTAX      TransportAddress 
MAX-ACCESS  read-only 
STATUS      current 
DESCRIPTION  
"<Definition> The source address of the data packet that contained the 
request used to activate the current message. If the current message was 
activated by internal logic (e.g., scheduling logic), the value of this 
object is implementation specific.
<Parameter Type> Status
<Object Identifier> 1.3.6.1.4.1.1206.4.2.3.6.29"
REFERENCE  "RFC 3419, December 2002" 
::= { signControl 29 }

-- 5.7.30	Message Requester Security Name Parameter 
dmsMsgRequesterSecurityName  OBJECT-TYPE 
SYNTAX      SnmpAdminString 
MAX-ACCESS  read-only 
STATUS      current 
DESCRIPTION  
"<Definition> The security name associated with the data packet that 
contained the request used to activate the current message. If the current 
message was activated by internal logic (e.g., scheduling logic), the value 
of this object shall be the security name associated with the internal 
process that called the message (e.g., the ISO26048-1-
Action:fdActionSecurityName if called by the action table).
<Parameter Type> Status
<Object Identifier> 1.3.6.1.4.1.1206.4.2.3.6.30"
::= { signControl 30 }

-- 5.7.31	Pixel Service Duration V4 Parameter 
vmsPixelServiceDurationV4  OBJECT-TYPE 
SYNTAX      Integer32 (0..65535)
UNITS       "milliseconds" 
MAX-ACCESS  read-write 
STATUS      current  
DESCRIPTION  
"<Definition> Indicates the number of milliseconds to perform pixel service 
on an entire sign (i.e., 0 - 65.535 seconds). If the 
vmsPixelServiceDurationV4 expires during a pixel service routine, that 
routine shall be completed before stopping or restarting a new pixel service 
routine due to vmsPixelServiceFrequency. A value of zero disables pixel 
service.
<Parameter Type> Configuration
<Object Identifier> 1.3.6.1.4.1.1206.4.2.3.6.31"
::= { signControl 31 }



-- 5.8	Illumination/Brightness Objects 
illum  OBJECT-IDENTITY 
STATUS  current
DESCRIPTION
"<Definition> This node is an identifier used to group all objects supporting 
DMS sign illumination functions that are common to DMS devices. 
<Object Identifier> 1.3.6.1.4.1.1206.4.2.3.7"
::= { dms 7 }


-- 5.8.1	Illumination Control Parameter 
dmsIllumControl  OBJECT-TYPE 
SYNTAX      INTEGER {
                 other (1),         -- deprecated
                 photocell (2),
                 timer (3),
                 manual (4),        -- obsolete 
                 manualDirect (5),
                 manualIndexed (6) } 
MAX-ACCESS  read-write 
STATUS      current  
DESCRIPTION  
"<Definition> Indicates the method used to select the Brightness Level.
A DMS may subrange the values supported, as indicated.
<Format>
  other (1) - indicates that the Brightness Level is based on a 
     mechanism not defined by this standard; see manufacturer 
     documentation. This mode is DEPRECATED.
  photocell (2) - indicates that the Brightness Level is based on 
     photocell status. Support for this mode shall be supported if 
     user need 2.5.1.5 is selected.
  timer (3) - indicates that the Brightness Level is set by an internal 
     timer. The details of this timer are not defined by this standard.
  manual (4) - indicates that the Brightness Level must be changed via 
     the dmsIllumManLevel object. This mode is OBSOLETE.
  manualDirect (5) - indicates that a user can change the brightness output 
     to any of the brightness levels (dmsIllumNumBrightLevels) supported by 
     the sign. This is not the same as the number of brightness levels 
     defined within the table of the dmsIllumBrightnessValues object. 
  manualIndexed (6) - indicates that a user can change the brightness output
     to any of the rows defined within the table of the
     dmsIllumBrightnessValues object. 
The DMS shall support manualDirect, manualIndex, or both. Support for all 
other values is optional.

When switching to any of the manual modes (manual, manualDirect, 
manualIndexed) from any other mode, the current brightness level shall 
automatically be loaded into the dmsIllumManLevel object.

<Informative> In v02, the enumerated values of 'other' and 'manual' were 
deprecated to improve interoperability. In v04, the value of 'manual' was 
made obsolete.
<Parameter Type> Configuration
<Object Identifier> 1.3.6.1.4.1.1206.4.2.3.7.1"
DEFVAL  {photocell} 
::= { illum 1 }

-- 5.8.2	Maximum Illumination Photocell Level Parameter 
dmsIllumMaxPhotocellLevel  OBJECT-TYPE 
SYNTAX      Integer32 (0..65535) 
MAX-ACCESS  read-only 
STATUS      deprecated  
DESCRIPTION  
"<Definition> Indicates the maximum value given by the 
dmsIllumPhotocellLevelStatus-object.
<Superseded by> ISO26048-1-Srsa:fdSrsaPortMaxValue.FAL
<Informative> This object was deprecated in v04 and replaced with the more 
universal SRSA object.
<Parameter Type> Status
<Object Identifier> 1.3.6.1.4.1.1206.4.2.3.7.2"
::= { illum 2 }

-- 5.8.3	Status of Illumination Photocell Level Parameter 
dmsIllumPhotocellLevelStatus  OBJECT-TYPE 
SYNTAX      Integer32 (0..65535) 
MAX-ACCESS  read-only 
STATUS      deprecated  
DESCRIPTION  
"<Definition> Indicates the level of Ambient Light as a value ranging from 0 
(darkest) to the value of dmsIllumMaxPhotocellLevel object (brightest), based 
on the photocell detection. The dmsIllumPhotocellLevelStatus object is 
considered a virtual photocell level in that it may be algorithmically 
determined from one or more photocells and is the value used for calculations 
dealing with the brightness table. The algorithm used to determine the 
virtual level from the actual photocell readings is manufacturer specific to 
accommodate various hardware needs.
<Superseded by> ISO26048-1-Srsa:fdSrsaTypeValueStatsMfrValue.FAL
<Informative> This object was deprecated in v04 and replaced with the more 
universal SRSA object.
<Parameter Type> Status
<Object Identifier> 1.3.6.1.4.1.1206.4.2.3.7.3"
::= { illum 3 }

-- 5.8.4	Number of Illumination Brightness Levels Parameter 
dmsIllumNumBrightLevels  OBJECT-TYPE 
SYNTAX      Integer32 (0..255) 
MAX-ACCESS  read-only 
STATUS      current  
DESCRIPTION  
"<Definition> Indicates the number of individually selectable Brightness 
Levels supported by the device, excluding the OFF level (=value of zero [0]). 
This value indicates the total levels of brightness that this device 
supports, not the number of rows defined in the table of the 
dmsIllumBrightnessValues object.
<Parameter Type> Status
<Object Identifier> 1.3.6.1.4.1.1206.4.2.3.7.4"
::= { illum 4 }

-- 5.8.5	Status of Illumination Brightness Level Parameter 
dmsIllumBrightLevelStatus  OBJECT-TYPE 
SYNTAX      Integer32 (0..255) 
MAX-ACCESS  read-only 
STATUS      current  
DESCRIPTION  
"<Definition> Indicates the current Brightness Level of the device, ranging 
from 0 (OFF) to the maximum value given by the dmsIllumNumBrightLevels- 
object (Brightest).
<Parameter Type> Status
<Object Identifier> 1.3.6.1.4.1.1206.4.2.3.7.5"
::= { illum 5 }

-- 5.8.6	Illumination Manual Level Parameter 
dmsIllumManLevel  OBJECT-TYPE 
SYNTAX      Integer32 (0..255) 
MAX-ACCESS  read-write 
STATUS      current  
DESCRIPTION  
"<Definition> Indicates the desired value of the Brightness Level as a value 
ranging from 0 to the value of the dmsIllumNumBrightLevels-object when under 
manual control.
When the dmsIllumControl object is set to a value of 'manualDirect (5)' then 
the maximum value that this object can have is the total levels of brightness 
that this device supports. A user can calculate the direct manual light 
output as (65535 * (dmsIllumManLevel object value / dmsIllumNumBrightLevels 
object value)).
When the dmsIllumControl object is set to a value of 'manualIndexed (6)' then 
the maximum value that this object can be set to is the number of rows 
defined in the table of the dmsIllumBrightnessValues object.
If the device supports version 1 and the dmsIllumControl object is set to a 
value of 'manual (4)', then the deployment could be either (contact your 
vendor to determine which way is implemented)
<Parameter Type> Configuration
<Object Identifier> 1.3.6.1.4.1.1206.4.2.3.7.6"
::= { illum 6 }

-- 5.8.7	Illumination Brightness Values Parameter 
dmsIllumBrightnessValues  OBJECT-TYPE 
SYNTAX      OCTET STRING 
MAX-ACCESS  read-write 
STATUS      current  
DESCRIPTION  
"<Definition> . An OCTET STRING describing the sign's light output in 
relationship to the Photocell(s) detection of ambient light. 
<Format> For each light output level, there is a corresponding range of 
photocell levels. The number of light output levels transmitted is defined by 
the first byte of the data packet, but cannot exceed the value of the 
dmsIllumNumBrightLevels object. Setting the value of this object to a non-
supported or erroneous value shall lead to a wrongValue or inconsistentValue 
error, as appropriate. Cause of this error shall be denoted by the 
dmsIllumBrightnessValuesError object.
After a SET, an implementation may interpolate these entries to create a 
table with as many entries as needed, but the value of the object shall not 
be affected by such interpolations. 
For each light output level, there are three 16-bit values that occur in the 
following order: Light output level, Photocell level down, Photocell level 
up.
The light output level is a value between 0 (no light output) and 65535 
(maximum light output). Each step is 1/65535 of the maximum light output 
(linear scale).
The Photocell-level-down is the lowest photocell level allowed to maintain 
the light output level. If the photocell level goes below this point, the 
light output level goes down one light output level.
The Photocell-level-up is the highest photocell level for this light output 
level. If the photocell level goes above this point, the light output level 
goes up one light output level.
The photocell level (Up and Down) values may not exceed the value of the 
ISO26048-1-Srsa:fdSrsaPortMaxValue.FAL object.
The points transmitted should be selected so that there is no photocell level 
which does not have a light output level. Hysteresis is possible by defining 
the photocell-level-up at a level higher than the upper level's photocell-
level-down. 
The encoding of the structure shall consist of a one byte integer value 
indicating the number of rows in the table. This is followed by a series of 
OER encoded Strings of the following structure:
  SEQUENCE {
      lightOutput            INTEGER (0..65535),
      photocellLevelDown     INTEGER (0..65535),
      photocellLevelUp       INTEGER (0..65535) } 

If the sign does not support photocell and the dmsIllumControl object value 
is set to 'manualIndexed', then the values for the 'photocellLevelDown' and 
'photocellLevelUp' still need to be entered that the table does not cause any 
errors as defined in the dmsIllumBrightnessValuesError object. However, since 
no photocell is supported, the entered values for 'photocellLevelDown' and 
'photocellLevelUp' for the various 'lightOutputs' are meaningless.

<Parameter Type> Configuration
<Object Identifier> 1.3.6.1.4.1.1206.4.2.3.7.7"
::= { illum 7 }

-- 5.8.8	Brightness Values Error Parameter 
dmsIllumBrightnessValuesError  OBJECT-TYPE 
SYNTAX      INTEGER {
                 other (1),
                 none (2),
                 photocellGap (3),
                 negativeSlope (4),
                 tooManyLevels (5),
                 invalidData (6) } 
MAX-ACCESS  read-only 
STATUS      current  
DESCRIPTION  
"<Definition> Indicates the error encountered when the brightness table was 
SET.
<Format>
other(1) - is for a manufacturer specific indication when none of the 
     other possible values can be used. 
none(2)  - indicates that no error was encountered. 
photocellGap(3) - indicates that certain photocell levels do not have 
     an associated brightness level. 
negativeSlope(4) - indicates that the photocell range used to select a 
     brighter brightness level is lower or overlaps the photocell range 
     used to select a dimmer brightness level. Note that some signs 
     may allow a negative slope for special conditions without 
     generating an error; e.g., external illumination for a reflective sign 
     may be allowed to turn off during daylight conditions rather than 
     getting brighter.
tooManyLevels(5) - indicates that more brightness levels are defined 
     than are reported by dmsIllumNumBrightLevels. 
invalidData(6) - indicates a manufacturer defined condition of invalid 
     data not described by the other options.

<Parameter Type> Status
<Object Identifier> 1.3.6.1.4.1.1206.4.2.3.7.8"
::= { illum 8 }

-- 5.8.9	Status of Illumination Light Output Parameter 
dmsIllumLightOutputStatus  OBJECT-TYPE 
SYNTAX      Integer32 (0..65535) 
MAX-ACCESS  read-only 
STATUS      current  
DESCRIPTION  
"<Definition> Indicates the current physical light output value ranging from 
0 (darkest) to 65535 (maximum output).
<Parameter Type> Status
<Object Identifier> 1.3.6.1.4.1.1206.4.2.3.7.9"
::= { illum 9 }

-- 5.9	Scheduling Action Objects 
dmsSchedule  OBJECT-IDENTITY
STATUS  current 
DESCRIPTION
"<Definition> This node is an identifier used to group all DMS device-
specific objects supporting DMS sign timebased scheduling. 
<Object Identifier> 1.3.6.1.4.1.1206.4.2.3.8"
::= { dms 8 }


-- 5.9.1	Action Table Entries Parameter 
numActionTableEntries  OBJECT-TYPE 
SYNTAX      Integer32 (0..255)
UNITS       "entries" 
MAX-ACCESS  read-only 
STATUS      current  
DESCRIPTION  
"<Definition> Indicates the number of rows that are stored in the 
dmsActionTable. See the Specification in association with Requirement 
3.5.10.4 to determine the number of actions required.
<Parameter Type> Status
<Object Identifier> 1.3.6.1.4.1.1206.4.2.3.8.1"
::= { dmsSchedule 1 }

-- 5.9.2	Action Table Parameter 
dmsActionTable  OBJECT-TYPE 
SYNTAX      SEQUENCE OF DmsActionEntry
MAX-ACCESS  not-accessible
STATUS      current 
DESCRIPTION "<Definition> A table containing a list of message codes. The 
scheduler (as defined in the dayPlanTable within NTCIP 1201) determines when 
a message shall be displayed. This table determines which message shall be 
activated.
Implementations that support the dmsActionTable (this table) and the 
fdActionTable (as definedin ISO 26048-1) shall allow any instance of 
fdActionPointer to reference any row of the dmsActionTable.
<Informative> This action table identifies the message to be placed into the 
schedule row of the dmsMessageTable (e.g., the MultiString is stored in 
dmsMessageMultistring.6.1) 
<Table Type> static
<Object Identifier> 1.3.6.1.4.1.1206.4.2.3.8.2"
::= {dmsSchedule 2}

dmsActionEntry OBJECT-TYPE
SYNTAX      DmsActionEntry
MAX-ACCESS  not-accessible
STATUS      current 
DESCRIPTION "<Definition> Parameters of the DMS Action Table."
INDEX {dmsActionIndex}
::= {dmsActionTable 1}

DmsActionEntry ::= SEQUENCE {
   dmsActionIndex        Integer32,
   dmsActionMsgCode      MessageIDCode } 

-- 5.9.2.1	Action Index Parameter 
dmsActionIndex  OBJECT-TYPE 
SYNTAX      Integer32 (1..255) 
MAX-ACCESS  read-only 
STATUS      current  
DESCRIPTION  
"<Definition> Enumerated listing of row entries. The value of this object 
cannot exceed the value of the numActionTableEntries - object.
<Parameter Type> Status
<Object Identifier> 1.3.6.1.4.1.1206.4.2.3.8.2.1.1"
::= { dmsActionEntry 1 }

-- 5.9.2.2	Action Message Code Parameter 
dmsActionMsgCode  OBJECT-TYPE 
SYNTAX      MessageIDCode 
MAX-ACCESS  read-write 
STATUS      current  
DESCRIPTION  
"<Definition> A code indicating the message memory type, the message number 
and the associated message-specific CRC as indicated within the message 
table.
Setting the CRC portion of this object to all zeros allows a message to 
become activated without the CRC validation process.
<Parameter Type> Configuration
<Object Identifier> 1.3.6.1.4.1.1206.4.2.3.8.2.1.2"
DEFVAL  {'0000000000'h}
::= { dmsActionEntry 2 }

-- 5.10	Auxiliary I/O Objects 
-- The objects originally defined under this node were moved to the 
-- 'global' node and NTCIP 1201 with the publication of NTCIP 1201 v02 
-- Amendment 2. 

-- 5.11	Sign Status 
dmsStatus  OBJECT-IDENTITY 
STATUS  current
DESCRIPTION
"<Definition> This node is an identifier used to group all objects supporting 
  DMS sign status monitoring functions that are common to DMS devices. 
<Object Identifier> 1.3.6.1.4.1.1206.4.2.3.9"
::= { dms 9 }

-- 5.11.1	Core Status 

-- 5.11.1.1	Number of Rows in MULTI Field Table Parameter 
statMultiFieldRows  OBJECT-TYPE 
SYNTAX      Integer32 (0..255)
UNITS       "rows" 
MAX-ACCESS  read-only 
STATUS      current  
DESCRIPTION  
"<Definition> Indicates the number of rows in the statMultiFieldTable that 
are currently being used.
<Parameter Type> Status
<Object Identifier> 1.3.6.1.4.1.1206.4.2.3.9.1"
::= { dmsStatus 1 }

-- 5.11.1.2	MULTI Field Table Parameter 
statMultiFieldTable  OBJECT-TYPE 
SYNTAX      SEQUENCE OF StatMultiFieldEntry
MAX-ACCESS  not-accessible
STATUS      current 
DESCRIPTION "<Definition> A table containing the currently displayed value of 
a specified Field. The number of rows  is given by the value of 
statMultiFieldRows-object.
<Table Type> static
<Object Identifier> 1.3.6.1.4.1.1206.4.2.3.9.2"
::= {dmsStatus 2}

statMultiFieldEntry OBJECT-TYPE
SYNTAX      StatMultiFieldEntry
MAX-ACCESS  not-accessible
STATUS      current 
DESCRIPTION "<Definition> Parameters of the Status Multi Field Table."
INDEX {statMultiFieldIndex}
::= {statMultiFieldTable 1}

StatMultiFieldEntry ::= SEQUENCE {
   statMultiFieldIndex        Integer32,
   statMultiFieldCode         Integer32,
   statMultiCurrentFieldValue MultiString} 

-- 5.11.1.2.1	MULTI Field Index Parameter 
statMultiFieldIndex  OBJECT-TYPE 
SYNTAX      Integer32 (1..255) 
MAX-ACCESS  read-only 
STATUS      current  
DESCRIPTION  
"<Definition> The index into this table indicating the sequential order of 
the field within the MULTI-string.
<Parameter Type> Status
<Object Identifier> 1.3.6.1.4.1.1206.4.2.3.9.2.1.1"
::= { statMultiFieldEntry 1 }

-- 5.11.1.2.2	Code of MULTI Field Parameter 
statMultiFieldCode  OBJECT-TYPE 
SYNTAX      Integer32 (1..255) 
MAX-ACCESS  read-only 
STATUS      current  
DESCRIPTION  
"<Definition> Indicates the ID of the statMultiCurrentFieldValue-object. The 
field codes are indicated under the 'Field'-tag in MULTI.
<Parameter Type> Status
<Object Identifier> 1.3.6.1.4.1.1206.4.2.3.9.2.1.2"
::= { statMultiFieldEntry 2 }

-- 5.11.1.2.3	Current Value of the MULTI Field Parameter 
statMultiCurrentFieldValue  OBJECT-TYPE 
SYNTAX      MultiString (SIZE (0..50)) 
MAX-ACCESS  read-only 
STATUS      current  
DESCRIPTION  
"<Definition> Indicates the value of the field in the currently displayed 
MULTI-message.
<Informative> The value provides the value of the field, which can contain 
embedded tags (e.g., to change font) but not embedded field tags.
<Parameter Type> Status
<Object Identifier> 1.3.6.1.4.1.1206.4.2.3.9.2.1.3"
::= { statMultiFieldEntry 3 }

-- 5.11.1.3	Current Speed Parameter 
dmsCurrentSpeed  OBJECT-TYPE 
SYNTAX      Integer32 (0..255)
UNITS       "kilometers per hour" 
MAX-ACCESS  read-only 
STATUS      deprecated  
DESCRIPTION  
"<Definition> The current speed value detected by the attached device. The 
speed is in kilometers per hour (km/h). This value may vary from the 
displayed speed value due to application specific implementation.
<Superseded by> ISO26048-1-Srsa:fdSrsaPortValue.VSS.1
<Informative> This object was deprecated in NTCIP 1203 v04 and replaced by 
the more generic SRSA table that offers greater capabilities and can support 
multiple sensors.
<Parameter Type> Status
<Object Identifier> 1.3.6.1.4.1.1206.4.2.3.9.3"
::= { dmsStatus 3 }

-- 5.11.1.4	Current Speed Limit Parameter 
dmsCurrentSpeedLimit  OBJECT-TYPE 
SYNTAX      Integer32 (0..255)
UNITS       "kilometers per hour" 
MAX-ACCESS  read-write 
STATUS      current  
DESCRIPTION  
"<Definition> Indicates the current speed limit in kilometers per hour 
(km/h).
<Parameter Type> Configuration
<Object Identifier> 1.3.6.1.4.1.1206.4.2.3.9.4"
::= { dmsStatus 4 }

-- 5.11.1.5	Watchdog Failure Count Parameter 
watchdogFailureCount  OBJECT-TYPE 
SYNTAX      Counter32 
MAX-ACCESS  read-only 
STATUS      deprecated  
DESCRIPTION  
"<Definition> A counter indicating the number of watchdog failures that have 
been detected.
<Superseded by> ISO26048-1-Controller:fdWatchdogFailures
<Informative> This object was deprecated in v04 and replaced with the more 
universal fdWatchdogFailures object.
<Parameter Type> Status
<Object Identifier> 1.3.6.1.4.1.1206.4.2.3.9.5"
::= { dmsStatus 5 }

-- 5.11.1.6	Open Door Status Parameter 
dmsStatDoorOpen  OBJECT-TYPE 
SYNTAX      Integer32 (0..255) 
MAX-ACCESS  read-only 
STATUS      deprecated  
DESCRIPTION  
"<Definition> Indicates whether any of the doors to the controller cabinet or 
the sign housing are open. This is a bitmap; if a bit is set (= 1) then the 
door is open; if a bit not is not set, then the associated door is closed. 
Each door is associated with a bit (bit-door correlation order specified by 
manufacturer) allowing for up to 8 doors.
<Superseded by> ISO26048-1-Srsa:fdSrsaTypeWarning.FDO
<Informative> This object was deprecated in v04 and replaced with the more 
universal SRSA object.
<Parameter Type> Status
<Object Identifier> 1.3.6.1.4.1.1206.4.2.3.9.6"
::= { dmsStatus  6 }

-- 5.11.2	Status Error Objects 
statError  OBJECT-IDENTITY 
STATUS  current
DESCRIPTION
"<Definition> This node is an identifier used to group all objects supporting 
DMS sign message error status functions that are common to DMS devices. 
<Object Identifier> 1.3.6.1.4.1.1206.4.2.3.9.7"
::= { dmsStatus 7 }

-- 5.11.2.1	Controller Errors 

-- 5.11.2.1.1	Short Error Status Parameter 
shortErrorStatus  OBJECT-TYPE 
SYNTAX      NtcipIntegerBitmap16  
MAX-ACCESS  read-only 
STATUS      current  
DESCRIPTION  
"<Definition> A bitmap of summary errors. When a bit is set, the error is 
presently active. When a bit is clear the error is not currently active. If 
no sensor is present or supported (for a corresponding bit), the bit 
shall not be set. 
<Format>  The bits are defined as follows:
Bit 0- other - not defined by this standard, see the value of 
      dmsOtherShortErrorDescr.
      The value of other was deprecated in v02 and reinstated in v04.
Bit 1- communications error - this bit shall be set if any error 
      associated with the communications between the central 
      computer and the device occurs.
Bit 2- power error - this bit shall be set if any error is detected for any 
      power supply associated with any component (i.e., any bit set in 
      fdSrsaTypeWarning.FPA, FPS, or FPV) or if the generator fuel 
      level is below its minimum threshold or has an error 
      (i.e., any bit set in fdSrsaTypeWarning.FGF). 
Bit 3- attached device error - this bit shall be set if any error 
      associated with attached (supported, and enabled) external 
      devices occurs (i.e., any bit set in any fdSrsaTypeWarning object 
      that is not otherwise specified by other bots of this object).
Bit 4- lamp error - this bit shall be set if any errors associated with any 
      lamp occurs (i.e., any bit set in fdSrsaTypeWarning.MLS) This bit 
      is only applicable to devices that support lamps such as fiber optic 
      signs or front-illuminated reflective signs. This bit is not applicable 
      to lamps or fluorescent lights illuminating the housing or cabinet.
Bit 5- pixel error - this bit shall be set if any errors associated with any 
      pixel occurs (see the objects pixelFailureTableNumRows for NTCIP 1203 
      v01 deployments, and pixelFailureTableNumRows, and/or 
      dmsPixelFailureTestRows and dmsPixelFailureMessageRows for NTCIP 1203
      v02 deployments.). 
      This bit is only applicable to devices that support illumination of 
      individual pixels, but not to drum signs. 
      Note that certain sign technologies such as flip disk only sign may 
      not be able to determine pixel errors.
Bit 6- photocell error - this bit shall be set if any errors associated with 
      the supported light sensors occurs (i.e., any bit set in 
      fdSrsaTypeWarning.FAL). 
Bit 7- message error - this bit shall be set if any errors associated with 
      activating and/or displaying a message occurs (see the object
      dmsActivateMsgError).
Bit 8- controller error - this bit shall be set if any errors associated 
      with the controller occurs (i.e., any bit set in fdControllerStatus). 
Bit 9- temperature warning - this bit shall be set if any of the 
      temperature values detected by the device exceed 
      non-standardized temperature values (i.e., any bit set in 
      fdSrsaTypeWarning.FAT FET, or FPT). This bit is included to allow 
      vendors or agencies to define vendor- or agency-specific 
      threshold objects that indicate temperature changes that are of 
      interest but not dangerous to the life-expectancy of the device 
      (see also the 'critical temperature' bit)
Bit 10- climate-control system error - this bit shall be set if any errors 
      associated with the climate control systems such as fans and/or 
      heaters occurs (i.e., any bit set in fdSrsaTypeWarning.FAC, FDC, 
      FFO, FHO, or FTT).
Bit 11- critical temperature error - this bit shall be set if the critical 
      temperature as defined by the value of the critical temperature
      objects have been exceeded (i.e., any bit set in 
      fdSrsaTypeStatus.FAT, FET, or FPT).
Bit 12- Drum-sign Rotor error - This bit shall be set if any errors 
      associated with the rotor of a drum sign occurs (i.e., any bit set in
      fdSrsaTypeWarning.MDS).
Bit 13- This bit shall be set if any door to any DMS field component 
      (cabinet or housing) is open (i.e., any bit set in 
      fdSrsaTypeWarning.FDO).
Bit 14- Humidity warning - This bit shall be set if any humidity sensor
      sensor is reporting a humidity warning (i.e., any bit set in 
      fdSrsaTypeWarning.FAH or FEH).
Bit 15- invisible default text - this bit shall be set if the value for 
defaultBackgroudRGB is equal to the value of defaultForegroundRGB, which 
would result in the message not being visible unless the MULTI string itself 
specifies alternate colors. 

<Informative> To track a history of transient error conditions utilize the 
event logging table located in the Global Objects Definitions (NTCIP 1201).
<Parameter Type> Status
<Object Identifier> 1.3.6.1.4.1.1206.4.2.3.9.7.1"
::= { statError 1 }

-- 5.11.2.1.2	Controller Error Status Parameter 
controllerErrorStatus  OBJECT-TYPE 
SYNTAX      NtcipIntegerBitmap8 
MAX-ACCESS  read-only 
STATUS      deprecated  
DESCRIPTION  
"<Definition> A bitmap of controller related errors where the bits are 
defined as follows:
<Format>
  Bit 0- other controller error
  Bit 1- PROM error
  Bit 2- program/processor error
  Bit 3- RAM error
  Bit 4- Controller to display interface error
If a bit is set to one (1), then the associated error is existing; if the bit 
is set to zero (0), then the associated error is not existing.
<Superseded by> ISO26048-1-Controller:fdControllerStatus
<Informative> This object was deprecated in NTCIP 1203 v04 for the new global 
object solution.
<Parameter Type> Status
<Object Identifier> 1.3.6.1.4.1.1206.4.2.3.9.7.10"
::= { statError 10 }

-- 5.11.2.1.3	Other Short Error Description Parameter 
dmsOtherShortErrorDescr  OBJECT-TYPE 
SYNTAX      SnmpAdminString  
MAX-ACCESS  read-only 
STATUS      current  
DESCRIPTION  
"<Definition> A textual description of the 'other' error causing Bit 0 of 
shortErrorStatus to be set. This shall be a zero-length string when Bit 0 of 
shortErrorStatus is not set. The language used for this text-based message 
shall be as defined by ISO26048-1-Controller:fdDefaultLanguage.
<Parameter Type> Status
<Object Identifier> 1.3.6.1.4.1.1206.4.2.3.9.7.1"
::= { statError 39 }

-- 5.11.2.2	Power Status Data 

-- 5.11.2.2.1	Power Failure Status Map Parameter 
dmsPowerFailureStatusMap  OBJECT-TYPE 
SYNTAX      OCTET STRING (SIZE (0..64)) 
MAX-ACCESS  read-only 
STATUS      deprecated  
DESCRIPTION  
"<Definition> Indicates whether each power supply within the sign has failed. 
If a power supply has failed, its associated bit is set to one (1). The size 
of this object shall always present one bit for each power supply supported 
by the system, but shall not contain more than seven bits that are not 
associated with any power supply. 
A power supply is a local supply of subsystem power, such as a voltage 
regulator. Further information about each failed subsystem may be found in 
the dmsPowerStatusTable. If any bit within this object is set, then the 
'power error' bit within the shortErrorStatus object shall also be set.
<Superseded by> ISO26048-1-Srsa:fdSrsaTypeStatus.FPS
<Informative> This object was deprecated in NTCIP 1203 v04 and replaced with 
the more universal SRSA object.
<Parameter Type> Status
<Object Identifier> 1.3.6.1.4.1.1206.4.2.3.9.7.11"
::= { statError 11 }

-- 5.11.2.2.2	Number of Rows in Power Table Parameter 
dmsPowerNumRows  OBJECT-TYPE 
SYNTAX      Integer32 (0..512)
UNITS       "rows" 
MAX-ACCESS  read-only 
STATUS      deprecated  
DESCRIPTION  
"<Definition> Indicates the number of rows in the dmsPowerStatusTable.
<Superseded by> ISO26048-1-Srsa:fdSrsaTypeCount.FPS
<Informative> This object was deprecated in NTCIP 1203 v04 and replaced with 
the more universal SRSA object.
<Parameter Type> Status
<Object Identifier> 1.3.6.1.4.1.1206.4.2.3.9.7.12"
::= { statError 12 }

-- 5.11.2.2.3	Power Status Table Parameter
dmsPowerStatusTable  OBJECT-TYPE 
SYNTAX      SEQUENCE OF DmsPowerStatusEntry
MAX-ACCESS  not-accessible
STATUS      deprecated
DESCRIPTION "<Definition> A table containing status information for each 
power supply within a DMS.
<Table Type> static
<Superseded by> ISO26048-1-Srsa:fdSrsaPortTable
<Informative> This object was deprecated in NTCIP 1203 v04 and replaced with 
the more universal SRSA object.
<Object Identifier> 1.3.6.1.4.1.1206.4.2.3.9.7.13"
::= {statError 13}

dmsPowerStatusEntry OBJECT-TYPE
SYNTAX      DmsPowerStatusEntry
MAX-ACCESS  not-accessible
STATUS      deprecated
DESCRIPTION "<Definition> An entry in the power status table.
<Superseded by> ISO26048-1-Srsa:fdSrsaPortEntry
<Informative> This object was deprecated in NTCIP 1203 v04 and replaced with 
the more universal SRSA object."
INDEX { dmsPowerIndex }
::= {dmsPowerStatusTable 1}

DmsPowerStatusEntry ::= SEQUENCE {
   dmsPowerIndex        Integer32,
   dmsPowerDescription  DisplayString,
   dmsPowerMfrStatus    DisplayString,
   dmsPowerStatus       INTEGER, 
   dmsPowerVoltage      Integer32,
   dmsPowerType         INTEGER}

-- 5.11.2.2.3.1	Power Index Parameter 
dmsPowerIndex  OBJECT-TYPE 
SYNTAX      Integer32 (1..512) 
MAX-ACCESS  read-only 
STATUS      deprecated 
DESCRIPTION  
"<Definition> Index of the power supply status table. This index corresponds 
to the bit position within the dmsPowerFailureStatusMap bitmap: the row with 
index 1 corresponds to the low-order bit of the dmsPowerFailureStatusMap, 
etc.
<Superseded by> ISO26048-1-Srsa:fdSrsaPortIndex.FPS
<Informative> This object was deprecated in NTCIP 1203 v04 and replaced with 
the more universal SRSA object.
<Parameter Type> Status
<Object Identifier> 1.3.6.1.4.1.1206.4.2.3.9.7.13.1.1"
::= { dmsPowerStatusEntry 1 }

-- 5.11.2.2.3.2	Power Description Parameter 
dmsPowerDescription  OBJECT-TYPE 
SYNTAX      DisplayString (SIZE (0..64)) 
MAX-ACCESS  read-only 
STATUS      deprecated  
DESCRIPTION  
"<Definition> Human-readable description of the power supply. This value 
should provide enough information for maintenance personnel to identify the 
physical location of the power supply within the DMS. The description shall 
include a meaningful definition of the location where the power supply 
defined in this row is located within the DMS.
<Superseded by> ISO26048-1-Srsa:fdSrsaPortDescription.FPS
<Informative> This object was deprecated in NTCIP 1203 v04 and replaced with 
the more universal SRSA object.
<Parameter Type> Status
<Object Identifier> 1.3.6.1.4.1.1206.4.2.3.9.7.13.1.2"
::= { dmsPowerStatusEntry 2 }

-- 5.11.2.2.3.3	Power Manufacturer-Defined Status Parameter 
dmsPowerMfrStatus  OBJECT-TYPE 
SYNTAX      DisplayString (SIZE (0..64)) 
MAX-ACCESS  read-only 
STATUS      deprecated  
DESCRIPTION  
"<Definition> Indicates the current manufacturer-defined status of the power 
supply. This object allows a vendor to provide the operator with additional 
information.
<Superseded by> ISO26048-1-Srsa:fdSrsaPortTextStatus.FPS
<Informative> This object was deprecated in NTCIP 1203 v04 and replaced with 
the more universal SRSA object.
<Parameter Type> Status
<Object Identifier> 1.3.6.1.4.1.1206.4.2.3.9.7.13.1.3"
::= { dmsPowerStatusEntry 3 }

-- 5.11.2.2.3.4	Power Status Parameter 
dmsPowerStatus  OBJECT-TYPE 
SYNTAX      INTEGER {
                 other (1), -- deprecated 
                 noError (2),
                 powerFail (3), 
                 voltageOutOfSpec (4), 
                 currentOutOfSpec (5) } 
MAX-ACCESS  read-only 
STATUS      deprecated  
DESCRIPTION  
"<Definition> Indicates the current status of the indicated power supply.
<Format>
  other (1): Current status not defined by this standard. This value was
    deprecated in NTCIP 1203 v02.
  noError (2): No error detected.
  powerFail (3): The power supply is producing no output.
  voltageOutOfSpec (4): The power supply is producing voltage outside 
    the vendor recommended specification 
  currentOutOfSpec (5): The power supply is producing current outside of
    the vendor recommended specification.
<Superseded by> ISO26048-1-Srsa:fdSrsaPortValue.FPS
<Informative> This object was deprecated in NTCIP 1203 v04. The replacement 
object is limited to errors within the power supply; input and output 
voltages and currents are defined in separate entries within the SRSA table.
<Parameter Type> Status
<Object Identifier> 1.3.6.1.4.1.1206.4.2.3.9.7.13.1.4"
::= { dmsPowerStatusEntry 4 }

-- 5.11.2.2.3.5	Power Voltage Status Parameter 
dmsPowerVoltage  OBJECT-TYPE 
SYNTAX      Integer32 (0..65535)
UNITS       "hundredths of a volt" 
MAX-ACCESS  read-only 
STATUS      deprecated  
DESCRIPTION  
"<Definition> A voltage measurement in units of hundredths (1/100) of a volt. 
The maximum value (0xFFFF) corresponds to a voltage of 655.35 volts. AC 
voltages are given in RMS (Root Mean Squared) value.
<Superseded by> ISO26048-1-Srsa:fdSrsaPortValue.FxV, where x indicates the 
voltage being measured
<Informative> This object was deprecated in NTCIP 1203 v04. The SRSA table 
disambiguates between the input and output voltage.
<Parameter Type> Status
<Object Identifier> 1.3.6.1.4.1.1206.4.2.3.9.7.13.1.5"
::= { dmsPowerStatusEntry 5 }

-- 5.11.2.2.3.6	Power Status Type Parameter
dmsPowerType  OBJECT-TYPE 
SYNTAX      INTEGER {
                  other (1),
                  acLine (2),
                  generator (3),
                  solar (4),
                  batteryUPS (5),
                  ledSupply (6),
                  lampSupply (7) } 
MAX-ACCESS  read-only 
STATUS      deprecated  
DESCRIPTION  
"<Definition> Indicates the type of power source or power supply represented 
by the table row.
<Format>
   other: indicates that the power source or supply is not one of the
      types listed  below (see device manual), in which case the
      corresponding dmsPowerDescription field provides a
      description of the entity represented by the row.
   acLine: indicates that the row represents a source of AC  power  This
      is also reflected in the lineVolts object.;
   generator: indicates that the row represents a generator;
   solar: indicates that the row represents solar equipment;
   batteryUPS: indicates that the row represents a
      battery or UPS with no significant charging occurring. This
      is also reflected in the signVolts object.
   ledSupply: indicates that the row represents the power supply to
      one or more LED pixels.
   lampSupply: indicates that the row represents the power supply to
      one or more display lamps.
<Superseded by> ISO26048-1-Srsa:fdSrsaTypeCode
<Informative> This object was deprecated in NTCIP 1203 v04 and replaced with 
the more universal SRSA object.
<Parameter Type> Status
<Object Identifier> 1.3.6.1.4.1.1206.4.2.3.9.7.13.1.6"
::= { dmsPowerStatusEntry 6 }

-- 5.11.2.3	Climate Control Status Data 

-- 5.11.2.3.1	Fan Failure Parameter 
fanFailures  OBJECT-TYPE 
SYNTAX  OCTET STRING (SIZE (0..4)) 
MAX-ACCESS  read-only 
STATUS      deprecated 
DESCRIPTION  
"<Definition> Indicates whether each fan (system) within a DMS is capable of 
operating, expressed as a bitmap. If a fan (system) failed, its associated 
bit is set to one (1). Each fan system is associated with a bit (bit-fan 
correlation order specified by manufacturer) allowing for up to 32 fan 
systems to report failure status. A fan system is defined as a single fan, 
group of fans, sensors, or filter systems. Whether each bit specifies a fan 
or fan system is dependent on the manufacturer.
<Superseded by> dmsClimateCtrlStatusMap
<Informative> This object was deprecated in NTCIP 1203 v02 and replaced by a 
more generic object
<Parameter Type> Status
<Object Identifier> 1.3.6.1.4.1.1206.4.2.3.9.7.8"
::= { statError 8 }

-- 5.11.2.3.2	Fan Test Activation Parameter 
fanTestActivation  OBJECT-TYPE 
SYNTAX      INTEGER {
                 other (1), 
                 noTest (2),
                 test (3) } 
MAX-ACCESS  read-write 
STATUS      deprecated 
DESCRIPTION  
"<Definition> Indicates the state of the fan testing. The actual test routine 
can vary among different manufacturers. The results of the fan test shall be 
stored in either the fanFailures-objects. Setting the value to test starts 
the test, meaning this test is executed once. The sign controller 
automatically sets the value of this object back to noTest after completion.
<Superseded by> dmsClimateCtrlTestActivation
<Informative> This object was deprecated in NTCIP 1203 v02, which also 
specifically discouraged the use of the value 'other'.
<Parameter Type> Control
<Object Identifier> 1.3.6.1.4.1.1206.4.2.3.9.7.9"
::= { statError 9 }

-- 5.11.2.3.3	Climate-control System Failure Status Map Parameter 
dmsClimateCtrlStatusMap  OBJECT-TYPE 
SYNTAX  OCTET STRING (SIZE (0..64)) 
MAX-ACCESS  read-only 
STATUS      deprecated 
DESCRIPTION  
"<Definition> Indicates whether each climate-control subsystem within the 
sign has failed. If a subsystem has failed, its associated bit is set to one 
(1).  The size of this object shall always present one bit for each climate 
control-subsystem supported by the system, but shall not contain more than 
seven bits that are not associated with any climate-control subsystem. 
Further information about each failed subsystem may be found in the 
dmsClimateCtrlStatusTable. If any bit within this object is set, then the 
'climate-control system error' bit within the shortErrorStatus object shall 
also be set.
<Superseded by> ISO26048-1-Srsa:fdSrsaTypeStatus for FAC, FDC, FFO, FHO, and 
FTT
<Informative> This object was deprecated in NTCIP 1203 v04 and replaced with 
the more universal SRSA object.
<Parameter Type> Status
<Object Identifier> 1.3.6.1.4.1.1206.4.2.3.9.7.14"
::= { statError 14 }

-- 5.11.2.3.4	Number of Rows in Climate-control Status Table Parameter 
dmsClimateCtrlNumRows  OBJECT-TYPE 
SYNTAX      Integer32
UNITS       "rows" 
MAX-ACCESS  read-only 
STATUS      deprecated 
DESCRIPTION  
"<Definition> Indicates the number of rows in the dmsClimateCtrlStatusTable.
<Superseded by> ISO26048-1-Srsa:fdSrsaTypeCount for FAC, FDC, FFO, FHO, and 
FTT
<Informative> This object was deprecated in NTCIP 1203 v04 and replaced with 
the more universal SRSA object.
<Parameter Type> Status
<Object Identifier> 1.3.6.1.4.1.1206.4.2.3.9.7.16"
::= { statError 16 }

-- 5.11.2.3.5	Climate-control System Failure Status Table Parameter
dmsClimateCtrlStatusTable  OBJECT-TYPE 
SYNTAX      SEQUENCE OF DmsClimateCtrlStatusEntry
MAX-ACCESS  not-accessible
STATUS      deprecated 
DESCRIPTION "<Definition> A table containing status information for each 
climate-control subsystem within a DMS.
<Superseded by> ISO26048-1-Srsa:fdSrsaPortTable for FAC, FDC, FFO, FHO, and 
FTT
<Informative> This object was deprecated in NTCIP 1203 v04 and replaced with 
the more universal SRSA object.<Table Type> static
<Object Identifier> 1.3.6.1.4.1.1206.4.2.3.9.7.17"
::= {statError 17}

dmsClimateCtrlStatusEntry OBJECT-TYPE
SYNTAX      DmsClimateCtrlStatusEntry
MAX-ACCESS  not-accessible
STATUS      deprecated 
DESCRIPTION "<Definition> An entry in the climate-control status table.
<Superseded by> ISO26048-1-Srsa:fdSrsaPortEntry for FAC, FDC, FFO, FHO, and 
FTT
<Informative> This object was deprecated in NTCIP 1203 v04 and replaced with 
the more universal SRSA object."
INDEX { dmsClimateCtrlIndex }
::= {dmsClimateCtrlStatusTable 1}

DmsClimateCtrlStatusEntry ::= SEQUENCE {
  dmsClimateCtrlIndex          Integer32,
  dmsClimateCtrlDescription    DisplayString,
  dmsClimateCtrlMfrStatus      DisplayString,
  dmsClimateCtrlErrorStatus    INTEGER,
  dmsClimateCtrlOnStatus       Integer32,
  dmsClimateCtrlTestActivation INTEGER,
  dmsClimateCtrlAbortReason    DisplayString,
  dmsClimateCtrlType           INTEGER} 

-- 5.11.2.3.5.1	Climate-control Index Parameter 
dmsClimateCtrlIndex  OBJECT-TYPE 
SYNTAX      Integer32 (1..512) 
MAX-ACCESS  read-only 
STATUS      deprecated  
DESCRIPTION  
"<Definition> Index of the climate control table. This index corresponds to 
the bit position within the dmsClimateCtrlStatusMap bitmap: the row with 
index 1 corresponds to the low-order bit of the dmsClimateCtrlStatusMap, etc.
<Superseded by> ISO26048-1-Srsa:fdSrsaPortIndex for FAC, FDC, FFO, FHO, and 
FTT
<Informative> This object was deprecated in NTCIP 1203 v04 and replaced with 
the more universal SRSA object.
<Parameter Type> Status
<Object Identifier> 1.3.6.1.4.1.1206.4.2.3.9.7.17.1.1"
::= { dmsClimateCtrlStatusEntry 1 }

-- 5.11.2.3.5.2	Climate-control Description Parameter 
dmsClimateCtrlDescription  OBJECT-TYPE 
SYNTAX  DisplayString (SIZE (0..64)) 
MAX-ACCESS  read-only 
STATUS      deprecated  
DESCRIPTION  
"<Definition> Human-readable description of the subsystem. This value should 
provide enough information for maintenance personnel to identify the type 
(AC, dehumidifier, heater, fan, etc) and physical location of the subsystem 
within the DMS. The description shall include a meaningful definition of the 
location where the sensor defined in this row is located within the DMS.
<Superseded by> ISO26048-1-Srsa:fdSrsaPortDescription for FAC, FDC, FFO, FHO, 
and FTT
<Informative> This object was deprecated in NTCIP 1203 v04 and replaced with 
the more universal SRSA object.
<Parameter Type> Status
<Object Identifier> 1.3.6.1.4.1.1206.4.2.3.9.7.17.1.2"
::= { dmsClimateCtrlStatusEntry 2 }

-- 5.11.2.3.5.3	Climate-Control Manufacturer-Defined Status Parameter 
dmsClimateCtrlMfrStatus  OBJECT-TYPE 
SYNTAX  DisplayString (SIZE (0..64)) 
MAX-ACCESS  read-only 
STATUS      deprecated  
DESCRIPTION  
"<Definition> Indicates the current manufacturer-defined status of the 
climate-control equipment. This object allows a vendor to provide the 
operator with additional information.
<Superseded by> ISO26048-1-Srsa:fdSrsaPortTextStatus for FAC, FDC, FFO, FHO, 
and FTT
<Informative> This object was deprecated in NTCIP 1203 v04 and replaced with 
the more universal SRSA object.
<Parameter Type> Status
<Object Identifier> 1.3.6.1.4.1.1206.4.2.3.9.7.17.1.3"
::= { dmsClimateCtrlStatusEntry 3 }

-- 5.11.2.3.5.4	Climate-control System Error Status Parameter 
dmsClimateCtrlErrorStatus  OBJECT-TYPE 
SYNTAX      INTEGER {
                 other (1), -- deprecated
                 noError (2),
                 fail (3), 
                 notMonitored (4)} 
MAX-ACCESS  read-only 
STATUS      deprecated  
DESCRIPTION  
"<Definition> Indicates the current status of the indicated subsystem.
<Superseded by> ISO26048-1-Srsa:fdSrsaPortStatus for FAC, FDC, FFO, FHO, and 
FTT
<Informative> This object was deprecated in NTCIP 1203 v04 and replaced with 
the more universal SRSA object.
<Parameter Type> Status
<Object Identifier> 1.3.6.1.4.1.1206.4.2.3.9.7.17.1.4"
::= { dmsClimateCtrlStatusEntry 4 }

-- 5.11.2.3.5.5	Climate-control On Status Parameter 
dmsClimateCtrlOnStatus  OBJECT-TYPE 
SYNTAX      Integer32 (0..1) 
MAX-ACCESS  read-only 
STATUS      deprecated  
DESCRIPTION  
"<Definition> Indicates whether the indicated climate-control subsystem is 
currently active. The bit orientation of 1 (set) indicates the system is on 
and a value of 0 (cleared) indicates the system is off.
<Superseded by> ISO26048-1-Srsa:fdSrsaPortValue for FAC, FDC, FFO, FHO, and 
FTT
<Informative> This object was deprecated in NTCIP 1203 v04 and replaced with 
the more universal SRSA object.
<Parameter Type> Status
<Object Identifier> 1.3.6.1.4.1.1206.4.2.3.9.7.17.1.5"
::= { dmsClimateCtrlStatusEntry 5 }

-- 5.11.2.3.5.6	Climate-control Test Activation Parameter 
dmsClimateCtrlTestActivation  OBJECT-TYPE 
SYNTAX      INTEGER {
                        noTest(2),
                        test(3),
                        testAborted(4) } 
MAX-ACCESS  read-write 
STATUS      deprecated  
DESCRIPTION  
"<Definition> Set to test(3) to activate the test for the climate-control 
device indicated by this row of the table. If the test completes normally, 
upon completion the sign shall set this object to noTest(2), with the results 
of the test appearing in the dmsClimateCtrlStatusMap and the 
dmsClimateCtrolErrorStatus objects and optionally in the 
dmsClimateCtrlMfrStatus object. If the test does not complete normally 
(either the sign declined to run the test at all or the test was started but 
aborted), the sign shall set this object to testAborted(4) and shall specify 
the reason for the abort in the dmsClimateCtrlAbortReason object. In the case 
of an abort, the dmsClimateCtrlStatusMap, dmsClimateCtrolErrorStatus,  and 
dmsClimateCtrlMfrStatus objects arenot be changed due to the test. At any 
time, this object can be set to noTest(2) to end any test in progress (in 
this case a subsequent read sees noTest(2) and not testAborted(4)). The value 
testAborted(4) is a read-only status - this object cannot be set to 
testAborted(4).
<Superseded by> ISO26048-1-Srsa:fdSrsaTypeTestActivation for FAC, FDC, FFO, 
FHO, and FTT
<Informative> This object was deprecated in NTCIP 1203 v04 and replaced with 
the more universal SRSA object.
<Parameter Type> Control
<Object Identifier> 1.3.6.1.4.1.1206.4.2.3.9.7.17.1.6"
::= { dmsClimateCtrlStatusEntry 6 }

-- 5.11.2.3.5.7	Climate-control Test Abort Reason Parameter 
dmsClimateCtrlAbortReason  OBJECT-TYPE 
SYNTAX  DisplayString (SIZE (0..64)) 
MAX-ACCESS  read-only 
STATUS      deprecated  
DESCRIPTION  
"<Definition> If the dmsClimateCtrlTestActivation object has a value of 
testAborted(4), this object indicates the manufacturer-defined reason as to 
why the climate-control test was aborted. This object is meaningless if 
dmsClimateCtrlTestActivation has any value other than testAborted(4).
<Superseded by> ISO26048-1-Srsa:fdSrsaTypeTestAbortReason for FAC, FDC, FFO, 
FHO, and FTT
<Informative> This object was deprecated in NTCIP 1203 v04 and replaced with 
the more universal SRSA object.
<Parameter Type> Status
<Object Identifier> 1.3.6.1.4.1.1206.4.2.3.9.7.17.1.7"
::= { dmsClimateCtrlStatusEntry 7 }

-- 5.11.2.3.5.8	Climate-Control Device Type Parameter 
dmsClimateCtrlType  OBJECT-TYPE 
SYNTAX      INTEGER {
                 other (1),
                 fansVentilation (2),
                 fansSignFace (3),
                 dehumidifier (4),
                 heatCabinet (5),
                 heatHousing (6),
                 heatSignFace (7),
                 airConditioningCabinet (8),
                 airConditioningHousing (9)}
MAX-ACCESS  read-only 
STATUS      deprecated  
DESCRIPTION  
"<Definition> Indicates the type of the climate control device described in 
this row of the table.
<Superseded by> ISO26048-1-Srsa:fdSrsaTypeCode for FAC, FDC, FFO, FHO, and 
FTT
<Informative> This object was deprecated in NTCIP 1203 v04 and replaced with 
the more universal SRSA object.
<Parameter Type> Status
<Object Identifier> 1.3.6.1.4.1.1206.4.2.3.9.7.17.1.8"
::= { dmsClimateCtrlStatusEntry 8 }

-- 5.11.2.4	Pixel Failure Data 

-- 5.11.2.4.1	Number of Rows in Pixel Failure Table Parameter 
pixelFailureTableNumRows  OBJECT-TYPE 
SYNTAX      Integer32 (0..65535)
UNITS       "rows" 
MAX-ACCESS  read-only 
STATUS      current  
DESCRIPTION  
"<Definition> The total number of rows contained in the pixelFailureTable 
each indicating failed pixels.
The value is the sum of the dmsPixelFailureTestRows and the 
dmsPixelFailureMessageRows objects.
<Parameter Type> Status
<Object Identifier> 1.3.6.1.4.1.1206.4.2.3.9.7.2"
::= { statError 2 }

-- 5.11.2.4.2	Pixel Failure Table Parameter 
pixelFailureTable  OBJECT-TYPE 
SYNTAX      SEQUENCE OF PixelFailureEntry
MAX-ACCESS  not-accessible
STATUS      current 
DESCRIPTION "<Definition> A table containing the X and Y location of a failed 
pixel. The number of rows is given by the value of pixelFailureTableNumRows -
object.
<Table Type> static
<Object Identifier> 1.3.6.1.4.1.1206.4.2.3.9.7.3"
::= {statError 3}

pixelFailureEntry	OBJECT-TYPE
SYNTAX      PixelFailureEntry
MAX-ACCESS  not-accessible
STATUS      current 
DESCRIPTION "<Definition> Parameters of the Pixel Failure Table. The 
detection of pixel failures during message displays shall be appended to the 
end of the table."
INDEX { pixelFailureDetectionType, pixelFailureIndex}
::= {pixelFailureTable 1}

PixelFailureEntry ::= SEQUENCE {
   pixelFailureDetectionType  INTEGER,
   pixelFailureIndex          Integer32,
   pixelFailureXLocation      Integer32,
   pixelFailureYLocation      Integer32,
   pixelFailureStatus         NtcipIntegerBitmap8} 

-- 5.11.2.4.2.1	Pixel Failure Detection Type Parameter 
pixelFailureDetectionType  OBJECT-TYPE 
SYNTAX      INTEGER {
                 other (1), -- deprecated 
                 pixelTest (2),
                 messageDisplay(3) } 
MAX-ACCESS  read-only 
STATUS      current  
DESCRIPTION  
"<Definition> Indicates the type of test/display that leads to the pixel 
failure entry.
Once a pixel is detected as failed, it is entered in the table with a type of 
either pixelTest or messageDisplay. In either case the failed pixel stays in 
the table until pixelTestActivation is set to either test or clearTable. 
<Format>
Detection type pixelTest and messageDisplay are considered different methods 
of testing for failed pixels. 
other: Not defined by this document; this value was deprecated in NTCIP 1203 
    v02.
pixelTest: This is considered a foreground processing method of failed pixel 
    detection. Failed pixels detected during a foreground pixel test are 
    entered in the pixelTest pixel failure type. During a foreground pixel 
    test, the message on the display may or may not stay present on the 
    display. 
messageDisplay: This is considered a background processing method of failed 
    pixel detection. During a background test, the readability/legibility of 
    the message shall not be affected by the test. If the manufacturer 
    supports background pixel test, failed pixels detected during a 
    background pixel test are entered in the messageDisplay pixel failure 
    type.
<Informative> In v02, the enumerated value of 'other' was deprecated to 
improve interoperability.
<Parameter Type> Status
<Object Identifier> 1.3.6.1.4.1.1206.4.2.3.9.7.3.1.1"
::= { pixelFailureEntry 1 }

-- 5.11.2.4.2.2	Pixel Failure Index Parameter 
pixelFailureIndex  OBJECT-TYPE 
SYNTAX      Integer32 (1..65535) 
MAX-ACCESS  read-only 
STATUS      current  
DESCRIPTION  
"<Definition> Enumerated listing of row entries. Within each 
pixelFailureDetectionType, entries shall start with one (1) and be 
sequential.
<Parameter Type> Status
<Object Identifier> 1.3.6.1.4.1.1206.4.2.3.9.7.3.1.2"
::= { pixelFailureEntry 2 }

-- 5.11.2.4.2.3	Pixel Failure X Location Parameter 
pixelFailureXLocation  OBJECT-TYPE 
SYNTAX      Integer32 (1..65535)
UNITS       "pixels" 
MAX-ACCESS  read-only 
STATUS      current  
DESCRIPTION  
"<Definition> Indicates the X location of the failed pixel. The X direction 
is the horizontal direction. The X location is counted from the left-most 
pixel in number of pixels.
<Parameter Type> Status
<Object Identifier> 1.3.6.1.4.1.1206.4.2.3.9.7.3.1.3"
::= { pixelFailureEntry 3 }

-- 5.11.2.4.2.4	Pixel Failure Y Location Parameter 
pixelFailureYLocation  OBJECT-TYPE 
SYNTAX      Integer32 (1..65535)
UNITS       "pixels" 
MAX-ACCESS  read-only 
STATUS      current  
DESCRIPTION  
"<Definition> Indicates the Y location of the failed pixel. The Y direction 
is the vertical direction. The Y location is counted from the top-most pixel 
in number of pixels.
<Parameter Type> Status
<Object Identifier> 1.3.6.1.4.1.1206.4.2.3.9.7.3.1.4"
::= { pixelFailureEntry 4 }

-- 5.11.2.4.2.5	Pixel Failure Status Parameter 
pixelFailureStatus  OBJECT-TYPE 
SYNTAX      NtcipIntegerBitmap8  
MAX-ACCESS  read-only 
STATUS      current  
DESCRIPTION  
"<Definition> Indicates the current status of the specified pixel and the 
operation which made this determination. This is a bit field with the 
following format:
<Format>
Bit 0:   0: Not stuck on / 1: Stuck On
Bit 1:   0: No Color Error / 1: Color Error 
Bit 2:   0: no electrical error / 1: electrical error
Bit 3:   0: no mechanical error / 1: mechanical error
Bit 4:   0: Not stuck off / 1: Stuck off
Bit 5:   0: No partial failure / 1: Partial failure - a partial failure 
indicates a loss of pixel functionality that does not affect the full 
luminance or visible area of a pixel. For example, if an LED DMS uses 
multiple redundant LEDs at each pixel, the failure of a single LED at a given 
pixel would be flagged as a partial failure. A partial failure indicates that 
the pixel is still functioning, but with reduced visibility.
<Parameter Type> Status
<Object Identifier> 1.3.6.1.4.1.1206.4.2.3.9.7.3.1.5"
::= { pixelFailureEntry 5 }

-- 5.11.2.4.3	Pixel Test Activation Parameter 
pixelTestActivation  OBJECT-TYPE 
SYNTAX      INTEGER {
                 other (1), -- deprecated 
                 noTest (2),
                 test (3),
                 clearTable (4) } 
MAX-ACCESS  read-write 
STATUS      current  
DESCRIPTION  
"<Definition> Indicates the state of the pixel testing. The actual test 
routine can vary among different manufacturers. The results of the pixel 
failure test shall be stored in the pixel failure table. 
<Format>
  other: the meaning of this value is not defined in this document; this 
    value was deprecated in NTCIP 1203 v02.
  noTest: Receiving this value in response to a GetRequest indicates that 
    the sign is not currently undergoing a pixel test. The value 'noTest' is 
    not valid in a SetRequest.
  test: Setting the value to 'test' clears both the pixel failure table and
    the pixelFailureTableNumRows object (for both 'messageDisplay' and 
    'pixelTest' types) and starts the pixel test, meaning this test is 
    executed once. Pixel failures identified by this test are entered into 
    the pixelFailureTable with pixelFailureDetectionType equal to 
    'pixelTest'. The sign controller automatically sets the value of this
    object back to 'noTest' after completion. Receiving this value in 
    response to a GetRequest indicates that the sign is still undergoing a 
    previous test.
  clearTable: Setting the value to 'clearTable' clears both the pixel failure  
    table and the pixelFailureTableNumRows object for both 'messageDisplay' 
    and 'pixelTest' types. The sign controller automatically sets the value 
    of this object back to 'noTest' after completion. Receiving this value in 
    response to a GetRequest indicates that the sign is still clearing the 
    table from a previous command.

<Informative> Versions of this object prior to NTCIP 1203 v04 were ambiguous 
regarding (1) the device transitioning the value 'clearTable' to 'noTest' 
once the table was cleared, (2) the possibility of using the 'noTest' value 
in a SetRequest, and (3) the meaning of a 'clearTable' value in a response to 
a GetRequest. 
In v02, the enumerated value of 'other' is RETIRED to improve 
interoperability.
<Parameter Type> Control
<Object Identifier> 1.3.6.1.4.1.1206.4.2.3.9.7.4"
DEFVAL  {noTest}
::= { statError 4 }

-- 5.11.2.4.4	Pixel Status Table Parameter
pixelStatusTable  OBJECT-TYPE 
SYNTAX      SEQUENCE OF PixelStatusEntry
MAX-ACCESS  not-accessible
STATUS      current 
DESCRIPTION "<Definition> A table containing a bitmap of all pixels. Because 
the bitmap may be too large for a single data packet, the bitmap is broken 
into blocks (represented by a dmsPixelStatus object). The number of rows is 
determined by the number of pixels in the sign and the maximum size of the 
dmsPixelStatus object. 
<Table Type> static
<Object Identifier> 1.3.6.1.4.1.1206.4.2.3.9.7.18"
::= {statError 18}

pixelStatusEntry	OBJECT-TYPE
SYNTAX      PixelStatusEntry
MAX-ACCESS  not-accessible
STATUS      current 
DESCRIPTION "<Definition> Parameters of the Pixel Status Table."
INDEX { dmsPixelStatusIndex}
::= {pixelStatusTable 1}

PixelStatusEntry ::= SEQUENCE {
   dmsPixelStatusIndex    Integer32,
   dmsPixelStatus         OCTET STRING,
   dmsPixelStatusV4       ITSBitmap } 

-- 5.11.2.4.4.1	Pixel Status Index Parameter
dmsPixelStatusIndex  OBJECT-TYPE 
SYNTAX      Integer32 (1..255) 
MAX-ACCESS  read-only 
STATUS      current  
DESCRIPTION  
"<Definition> Index of the pixel status table. This index corresponds to one 
entry of maximum size of 400 octets containing the status of each pixel 
within the sign.
<Parameter Type> Status
<Object Identifier> 1.3.6.1.4.1.1206.4.2.3.9.7.18.1.1"
::= { pixelStatusEntry 1 }

-- 5.11.2.4.4.2	Pixel Status Parameter 
dmsPixelStatus  OBJECT-TYPE 
SYNTAX      OCTET STRING (SIZE(1..400)) 
MAX-ACCESS  read-only 
STATUS      deprecated  
DESCRIPTION  
"<Definition> Indicates whether a pixel within the sign has failed. 

Indicates the status of each pixel within the sign. Each bit within this 
object is associated with an individual pixel. If a pixel has an error the 
associated bit shall be one (1). If a pixel has no error, the associated bit 
shall be zero (0).

The lowest-order bit corresponds to the top-left pixel of the sign face; the 
next bit corresponds to the next pixel to the right, etc. At the end of a 
pixel row, the next bit corresponds to the leftmost bit of the row below. If 
any bit within this object is set, then the 'pixel error' bit within the 
shortErrorStatus object shall also be set. This object value is changed when 
any type of pixel test within pixelTestActivation has completed.

Each row entry of this table contains a maximum of 400 octets which is 
equivalent to 3200 pixels per row entry. The last entry of this table does 
not need to be 400 octets but the preceding entries do. Any remaining bits 
within the final byte of the last entry of this table shall be zero.

<Superseded by> dmsPixelStatusV4
<Informative> This object was deprecated in NTCIP 1203 v04 because the 
definition of this object was determined to be ambiguous since an OCTET 
STRING does not have a clearly defined 'lowest order bit'.
<Parameter Type> Status
<Object Identifier> 1.3.6.1.4.1.1206.4.2.3.9.7.18.1.2"
::= { pixelStatusEntry 2 }

-- 5.11.2.4.4.3	Pixel Status Parameter Version 4
dmsPixelStatusV4  OBJECT-TYPE 
SYNTAX      ITSBitmap (SIZE (0..400))  
MAX-ACCESS  read-only 
STATUS      current  
DESCRIPTION  
"<Definition> Indicates whether a pixel within the sign has failed. 

Indicates the status of each pixel within the sign. Each bit within this 
object is associated with an individual pixel. If a pixel has an error the 
associated bit shall be one (1). If a pixel has no error, the associated bit 
shall be zero (0).

The highest-order bit of the first octet of the first entry table corresponds 
to the top-left pixel of the sign face; the next bit (i.e., the second-to-
highest-order bit of the first octet of the first entry) corresponds to the 
next pixel to the right, etc. At the end of an octet, the next bit is the 
highest-order bit of the following octet. At the end of a pixel row, the next 
pixel is the leftmost pixel of the row below. At the end of 3200 pixels (400 
octets) the next pixel is encoded in the highest-order bit of the first octet 
of the second entry in the table, etc.

If any bit within any instance of this object type has a value of one (1), 
the 'pixel error' bit within the shortErrorStatus object shall also be set. 
This object value is changed when any type of pixel test within 
pixelTestActivation has completed.

Each row entry of this table, except for the final row, shall contain 400 
octets, which is equivalent to 3200 pixels. The last entry of this table 
shall use the minimum number of octets possible to encode the remaining 
pixels supported by the sign. Any remaining bits within the final octet of 
the last entry of this table shall be zero.
<Parameter Type> Status
<Informative> A 10x10 pixel sign with the left-most pixel in the top two rows 
reporting failures would indicate the value 0x80 20 00 00 00 00 00 00 00 00 
00 00 00
<Object Identifier> 1.3.6.1.4.1.1206.4.2.3.9.7.18.1.3"
::= { pixelStatusEntry 3 }

-- 5.11.2.4.5	Number of Pixel Failures from Pixel Test Parameter
dmsPixelFailureTestRows  OBJECT-TYPE 
SYNTAX      Integer32 (0..65535)
UNITS       "rows" 
MAX-ACCESS  read-only 
STATUS      current  
DESCRIPTION  
"<Definition> Indicates the number of rows in the pixelFailureTable with a 
pixelFailureDetectionType of 'pixelTest'.
<Parameter Type> Status
<Object Identifier> 1.3.6.1.4.1.1206.4.2.3.9.7.19"
::= { statError 19 }

-- 5.11.2.4.6	Number of Pixel Failures from Message Display Parameter
dmsPixelFailureMessageRows  OBJECT-TYPE 
SYNTAX      Integer32 (0..65535)
UNITS       "rows" 
MAX-ACCESS  read-only 
STATUS      current  
DESCRIPTION  
"<Definition> Indicates the number of rows in the pixelFailureTable with a 
pixelFailureDetectionType of 'messageDisplay'.
<Parameter Type> Status
<Object Identifier> 1.3.6.1.4.1.1206.4.2.3.9.7.20"
::= { statError 20 }

-- 5.11.2.5	Lamp Status Data 

-- 5.11.2.5.1	Stuck On Lamp Failure Parameter 
lampFailureStuckOn  OBJECT-TYPE 
SYNTAX  OCTET STRING (SIZE (0..255)) 
MAX-ACCESS  read-only 
STATUS      deprecated  
DESCRIPTION  
"<Definition> Indicates whether each lamp within the sign is stuck on as a 
bitmap. If a lamp is stuck on, its associated bit is set to one (1). The size 
of this object shall always present one bit for each lamp supported by the 
DMS, but shall not contain more than seven bits that are not associated with 
any lamp. The lamp error bit in shortErrorStatus shall be set if any bit in 
lampFailureStuckOff is set.
The size of this object shall always present one bit for each lamp supported 
by the DMS, regardless of the failure status of the individual lamps.
<Superseded by> ISO26048-1-Srsa:fdSrsaTypeWarning.MLS
<Informative> This object was deprecated in NTCIP 1203 v04 and replaced with 
the more universal SRSA object.
<Parameter Type> Status
<Object Identifier> 1.3.6.1.4.1.1206.4.2.3.9.7.5"
::= { statError 5 }

-- 5.11.2.5.2	Stuck Off Lamp Failure Parameter 
lampFailureStuckOff  OBJECT-TYPE 
SYNTAX  OCTET STRING (SIZE (0..255)) 
MAX-ACCESS  read-only 
STATUS      deprecated  
DESCRIPTION  
"<Definition> Indicates whether each lamp within the sign is stuck off as a 
bitmap. If a lamp is stuck off, its associated bit is set to one (1). The 
size of this object shall always present one bit for each lamp supported by 
the DMS, but shall not contain more than seven bits that are not associated 
with any lamp. The lamp error bit in shortErrorStatus shall be set if any bit 
in lampFailuresStuckOn is set.
The size of this object shall always present one bit for each lamp supported 
by the DMS, regardless of the failure status of the individual lamps.
<Superseded by> ISO26048-1-Srsa:fdSrsaTypeWarning.MLS
<Informative> This object was deprecated in NTCIP 1203 v04 and replaced with 
the more universal SRSA object.
<Parameter Type> Status
<Object Identifier> 1.3.6.1.4.1.1206.4.2.3.9.7.6"
::= { statError 6 }

-- 5.11.2.5.3	Lamp Test Activation Parameter 
lampTestActivation  OBJECT-TYPE 
SYNTAX      INTEGER {
                 other (1), -- deprecated 
                 noTest (2),
                 test (3) } 
MAX-ACCESS  read-write 
STATUS      deprecated  
DESCRIPTION  
"<Definition> Indicates the state of the lamp testing. The actual test 
routine can vary among different manufacturers. The results of the lamp 
failure test shall be stored appropriately, in the lampFailureStuckOn- and/or 
in the lampFailureStuckOff-objects. In v02, the enumerated value of 'other' 
was deprecated to improve interoperability.
Setting the value to test starts the test, meaning this test is executed 
once. The sign controller shall automatically set the value of this object 
back to noTest after completion. Activation of lamp test shall clear the 
object lampFailureStuckOn and lampFailureStuckOff, the lamp status table, and 
the 'lamp fail' error bit in shortErrorStatus. Results of the lamp test shall 
update these two objects, the table and the error bit.
<Superseded by> ISO26048-1-Srsa:fdSrsaTypeTestActivation.MLS
<Informative> This object was deprecated in NTCIP 1203 v04 and replaced with 
the more universal SRSA object.
<Parameter Type> Control
<Object Identifier> 1.3.6.1.4.1.1206.4.2.3.9.7.7"
DEFVAL  {noTest} 
::= { statError 7 }

-- 5.11.2.5.4	Number of Rows in Lamp Status Table Parameter 
dmsLampNumRows  OBJECT-TYPE 
SYNTAX      Integer32 (0..2040)
UNITS       "rows" 
MAX-ACCESS  read-only 
STATUS      deprecated  
DESCRIPTION  
"<Definition> Indicates the number of rows in the dmsLampStatusTable. The 
number of rows is equal to the total number of lamps contained in the DMS, 
regardless of the failure status of the individual lamps.
<Superseded by> ISO26048-1-Srsa:fdSrsaTypeCount.MLS
<Informative> This object was deprecated in NTCIP 1203 v04 and replaced with 
the more universal SRSA object.
<Parameter Type> Status
<Object Identifier> 1.3.6.1.4.1.1206.4.2.3.9.7.23"
::= { statError 23 }

-- 5.11.2.5.5	Lamp Status Table Parameter 
dmsLampStatusTable  OBJECT-TYPE 
SYNTAX      SEQUENCE OF DmsLampStatusEntry
MAX-ACCESS  not-accessible
STATUS      deprecated
DESCRIPTION "<Definition> A table containing status information for each lamp 
within a DMS.
<Table Type> static
<Superseded by> ISO26048-1-Srsa:fdSrsaPortTable.MLS
<Informative> This object was deprecated in NTCIP 1203 v04 and replaced with 
the more universal SRSA object.
<Object Identifier> 1.3.6.1.4.1.1206.4.2.3.9.7.24"
::= {statError 24}

dmsLampStatusEntry OBJECT-TYPE
SYNTAX      DmsLampStatusEntry
MAX-ACCESS  not-accessible
STATUS      deprecated
DESCRIPTION "<Definition> An entry in the lamp status table.
<Superseded by> ISO26048-1-Srsa:fdSrsaPortEntry.MLS
<Informative> This object was deprecated in NTCIP 1203 v04 and replaced with 
the more universal SRSA object.
"
INDEX { dmsLampIndex }
::= {dmsLampStatusTable 1}

DmsLampStatusEntry ::= SEQUENCE {
   dmsLampIndex        Integer32,
   dmsLampDescription  DisplayString,
   dmsLampMfrStatus    DisplayString,
   dmsLampStatus       INTEGER,
   dmsLampPixelTop     Integer32,
   dmsLampPixelLeft    Integer32,
   dmsLampPixelBottom  Integer32,
   dmsLampPixelRight   Integer32} 

-- 5.11.2.5.5.1	Lamp Index Parameter 
dmsLampIndex  OBJECT-TYPE 
SYNTAX      Integer32 (1..2040) 
MAX-ACCESS  read-only 
STATUS      deprecated  
DESCRIPTION  
"<Definition> Index of the lamp status table. The number of rows in this 
table is equal to the value of the dmsLampNumRows object.
<Superseded by> ISO26048-1-Srsa:fdSrsaPortIndex.MLS
<Informative> This object was deprecated in NTCIP 1203 v04 and replaced with 
the more universal SRSA object.
<Parameter Type> Status
<Object Identifier> 1.3.6.1.4.1.1206.4.2.3.9.7.24.1.1"
::= { dmsLampStatusEntry 1 }

-- 5.11.2.5.5.2	Lamp Description Parameter 
dmsLampDescription  OBJECT-TYPE 
SYNTAX  DisplayString (SIZE (0..64)) 
MAX-ACCESS  read-only 
STATUS      deprecated  
DESCRIPTION  
"<Definition> Human-readable description of the lamp. This value should 
provide enough information for maintenance personnel to identify the physical 
location of the lamp within the DMS.
<Superseded by> ISO26048-1-Srsa:fdSrsaPortDescription.MLS
<Informative> This object was deprecated in NTCIP 1203 v04 and replaced with 
the more universal SRSA object.
<Parameter Type> Status
<Object Identifier> 1.3.6.1.4.1.1206.4.2.3.9.7.24.1.2"
::= { dmsLampStatusEntry 2 }

-- 5.11.2.5.5.3	Lamp Manufacturer-defined Status Parameter 
dmsLampMfrStatus  OBJECT-TYPE 
SYNTAX  DisplayString (SIZE (0..64)) 
MAX-ACCESS  read-only 
STATUS      deprecated  
DESCRIPTION  
"<Definition> Indicates the current manufacturer-defined status of the lamp. 
This object allows a vendor to provide the operator with additional 
information.
<Superseded by> ISO26048-1-Srsa:fdSrsaPortTextStatus.MLS
<Informative> This object was deprecated in NTCIP 1203 v04 and replaced with 
the more universal SRSA object.
<Parameter Type> Status
<Object Identifier> 1.3.6.1.4.1.1206.4.2.3.9.7.24.1.3"
::= { dmsLampStatusEntry 3 }

-- 5.11.2.5.5.4	Lamp Status Parameter 
dmsLampStatus  OBJECT-TYPE 
SYNTAX      INTEGER {
                 noError (2),
                 stuckOff (3),
                 stuckOn (4) } 
MAX-ACCESS  read-only 
STATUS      deprecated  
DESCRIPTION  
"<Definition> Indicates the current status of the indicated lamp.
<Superseded by> ISO26048-1-Srsa:fdSrsaPortStatus.MLS
<Informative> This object was deprecated in NTCIP 1203 v04 and replaced with 
the more universal SRSA object.
<Parameter Type> Status
<Object Identifier> 1.3.6.1.4.1.1206.4.2.3.9.7.24.1.4"
::= { dmsLampStatusEntry 4 }

-- 5.11.2.5.5.5	Lamp - Pixel Mapping Top Parameter 
dmsLampPixelTop  OBJECT-TYPE 
SYNTAX      Integer32 (1..65535) 
MAX-ACCESS  read-only 
STATUS      deprecated  
DESCRIPTION  
"<Definition> Indicates the topmost row of pixels served by this lamp. The 
top-most row on the sign face is row 1.
<Superseded by> dmsSrsaPixelsTop.MLS
<Informative> This object was deprecated in NTCIP 1203 v04 and replaced with 
the more universal SRSA object.
<Parameter Type> Status
<Object Identifier> 1.3.6.1.4.1.1206.4.2.3.9.7.24.1.5"
::= { dmsLampStatusEntry 5 }

-- 5.11.2.5.5.6	Lamp - Pixel Mapping Left Parameter 
dmsLampPixelLeft  OBJECT-TYPE 
SYNTAX      Integer32 (1..65535) 
MAX-ACCESS  read-only 
STATUS      deprecated  
DESCRIPTION  
"<Definition> Indicates the leftmost column of pixels served by this lamp. 
The left-most column on the sign face is column 1.
<Superseded by> dmsSrsaPixelsLeft.MLS
<Informative> This object was deprecated in NTCIP 1203 v04 and replaced with 
the more universal SRSA object.
<Parameter Type> Status
<Object Identifier> 1.3.6.1.4.1.1206.4.2.3.9.7.24.1.6"
::= { dmsLampStatusEntry 6 }

-- 5.11.2.5.5.7	Lamp - Pixel Mapping Bottom Parameter 
dmsLampPixelBottom  OBJECT-TYPE 
SYNTAX      Integer32 (1..65535) 
MAX-ACCESS  read-only 
STATUS      deprecated  
DESCRIPTION  
"<Definition> Indicates the bottommost row of pixels served by this lamp. The 
top-most row on the sign face is row 1.
<Superseded by> dmsSrsaPixelsBottom.MLS
<Informative> This object was deprecated in NTCIP 1203 v04 and replaced with 
the more universal SRSA object.
<Parameter Type> Status
<Object Identifier> 1.3.6.1.4.1.1206.4.2.3.9.7.24.1.7"
::= { dmsLampStatusEntry 7 }

-- 5.11.2.5.5.8	Lamp - Pixel Mapping Right Parameter 
dmsLampPixelRight  OBJECT-TYPE 
SYNTAX      Integer32  
MAX-ACCESS  read-only 
STATUS      deprecated  
DESCRIPTION  
"<Definition> Indicates the rightmost column of pixels served by this lamp. 
The left-most column on the sign face is column 1.
<Superseded by> dmsSrsaPixelsRight.MLS
<Informative> This object was deprecated in NTCIP 1203 v04 and replaced with 
the more universal SRSA object.
<Parameter Type> Status
<Object Identifier> 1.3.6.1.4.1.1206.4.2.3.9.7.24.1.8"
::= { dmsLampStatusEntry 8 }

-- 5.11.2.6	Drum Status Data 

-- 5.11.2.6.1	Drum Display Failure Status Map Parameter 
dmsDrumStatusMap  OBJECT-TYPE 
SYNTAX      OCTET STRING (SIZE (0..2)) 
MAX-ACCESS  read-only 
STATUS      deprecated  
DESCRIPTION  
"<Definition> Indicates whether each drum display subsystem within the sign 
has failed. If a subsystem has failed, its associated bit is set to one (1). 
The size of this object shall always present one bit for each drum supported 
by the DMS, but shall not contain more than seven bits that are not 
associated with any drum. 
Further information about each failed subsystem may be found in the 
dmsDrumStatusTable. If any bit within this object is set, then the 'drum sign 
error' bit within the shortErrorStatus object shall also be set.
<Superseded by> ISO26048-1-Srsa:fdSrsaTypeWarning.MDS
<Informative> This object was deprecated in NTCIP 1203 v04 and replaced with 
the more universal SRSA object.
<Parameter Type> Status
<Object Identifier> 1.3.6.1.4.1.1206.4.2.3.9.7.25"
::= { statError 25 }

-- 5.11.2.6.2	Number of Rows in Drum Status Table Parameter 
dmsDrumNumRows  OBJECT-TYPE 
SYNTAX      Integer32 (0..16)
UNITS       "rows" 
MAX-ACCESS  read-only 
STATUS      deprecated  
DESCRIPTION  
"<Definition> Indicates the number of rows in the dmsDrumStatusTable.
<Superseded by> ISO26048-1-Srsa:fdSrsaTypeCount.MDS
<Informative> This object was deprecated in NTCIP 1203 v04 and replaced with 
the more universal SRSA object.
<Parameter Type> Status
<Object Identifier> 1.3.6.1.4.1.1206.4.2.3.9.7.26"
::= { statError 26 }

-- 5.11.2.6.3	Drum Status Table Parameter 
dmsDrumStatusTable  OBJECT-TYPE 
SYNTAX      SEQUENCE OF DmsDrumStatusEntry
MAX-ACCESS  not-accessible
STATUS      deprecated
DESCRIPTION "<Definition> A table containing status information for each drum 
display unit within a DMS.
<Table Type> static
<Superseded by> ISO26048-1-Srsa:fdSrsaPortTable.MDS
<Informative> This object was deprecated in NTCIP 1203 v04 and replaced with 
the more universal SRSA object.
<Object Identifier> 1.3.6.1.4.1.1206.4.2.3.9.7.27"
::= {statError 27}

dmsDrumStatusEntry OBJECT-TYPE
SYNTAX      DmsDrumStatusEntry
MAX-ACCESS  not-accessible
STATUS      deprecated
DESCRIPTION "<Definition> An entry in the drum status table.
<Superseded by> ISO26048-1-Srsa:fdSrsaPortEntry.MDS
<Informative> This object was deprecated in NTCIP 1203 v04 and replaced with 
the more universal SRSA object."
INDEX { dmsDrumIndex }
::= {dmsDrumStatusTable 1}

DmsDrumStatusEntry ::= SEQUENCE {
   dmsDrumIndex       Integer32,
   dmsDrumDescription DisplayString,
   dmsDrumMfrStatus   DisplayString,
   dmsDrumStatus      INTEGER} 

-- 5.11.2.6.3.1	Drum Index Parameter 
dmsDrumIndex  OBJECT-TYPE 
SYNTAX      Integer32 (1..16) 
MAX-ACCESS  read-only 
STATUS      deprecated  
DESCRIPTION  
"<Definition> Index of the drum status table. This index corresponds to the 
bit position within the dmsDrumStatusMap bitmap: the row with index 1 
corresponds to the low-order bit of the dmsDrumStatusMap, etc. 
<Superseded by> ISO26048-1-Srsa:fdSrsaPortIndex.MDS
<Informative> This object was deprecated in NTCIP 1203 v04 and replaced with 
the more universal SRSA object.
<Parameter Type> Status
<Object Identifier> 1.3.6.1.4.1.1206.4.2.3.9.7.27.1.1"
::= { dmsDrumStatusEntry 1 }

-- 5.11.2.6.3.2	Drum Description Parameter 
dmsDrumDescription  OBJECT-TYPE 
SYNTAX  DisplayString (SIZE (0..64)) 
MAX-ACCESS  read-only 
STATUS      deprecated  
DESCRIPTION  
"<Definition> Human-readable description of the drum. This value should 
provide enough information for maintenance personnel to identify the physical 
location of the drum within the DMS. The description shall include a 
meaningful definition of the location where the sensor defined in this row is 
located within the DMS.
<Superseded by> ISO26048-1-Srsa:fdSrsaPortDescription.MDS
<Informative> This object was deprecated in NTCIP 1203 v04 and replaced with 
the more universal SRSA object.
<Parameter Type> Status
<Object Identifier> 1.3.6.1.4.1.1206.4.2.3.9.7.27.1.2"
::= { dmsDrumStatusEntry 2 }

-- 5.11.2.6.3.3	Drum Manufacturer-defined Status Parameter 
dmsDrumMfrStatus  OBJECT-TYPE 
SYNTAX  DisplayString (SIZE (0..64)) 
MAX-ACCESS  read-only 
STATUS      deprecated  
DESCRIPTION  
"<Definition> Indicates the current manufacturer-defined status of the drum. 
This object allows a vendor to provide the operator with additional 
information.
<Superseded by> ISO26048-1-Srsa:fdSrsaPortTextStatus.MDS
<Informative> This object was deprecated in NTCIP 1203 v04 and replaced with 
the more universal SRSA object.
<Parameter Type> Status
<Object Identifier> 1.3.6.1.4.1.1206.4.2.3.9.7.27.1.3"
::= { dmsDrumStatusEntry 3 }

-- 5.11.2.6.3.4	Drum Status Parameter 
dmsDrumStatus  OBJECT-TYPE 
SYNTAX      INTEGER {
                 other (1),
                 noError (2),
                 interlockError (3),
                 stuckError (4),
                 positionError (5),
                 positionUnknownError (6) } 
MAX-ACCESS  read-only 
STATUS      deprecated  
DESCRIPTION  
"<Definition> Indicates the current status of the indicated drum.
<Format>
  noError - the drum is working properly.
  interlockError - the drum has failed to lock into a correct display 
     position. It is hung up between two adjacent drum faces.
  stuckError - the drum cannot be moved from its present position, due 
     to a problem with the drum mechanism.
  positionError - the drum has moved to a position other than the 
     position requested by the DMS controller.
  positionUnknownError - the DMS controller cannot determine the 
     position of the drum.
<Superseded by> ISO26048-1-Srsa:fdSrsaPortValue.MDS
<Informative> This object was deprecated in NTCIP 1203 v04 and replaced with 
the more universal SRSA object.
<Parameter Type> Status
<Object Identifier> 1.3.6.1.4.1.1206.4.2.3.9.7.27.1.4"
::= { dmsDrumStatusEntry 4 }

-- 5.11.2.7	Light Sensor Status Data 

-- 5.11.2.7.1	Light Sensor Status Map Parameter 
dmsLightSensorStatusMap  OBJECT-TYPE 
SYNTAX      OCTET STRING (SIZE (0..2)) 
MAX-ACCESS  read-only 
STATUS      deprecated  
DESCRIPTION  
"<Definition> Indicates the operational status of all light sensors. If a 
light sensor is failed, the bit corresponding to the light sensor is set to 
1; otherwise 0. The size of this object shall always present one bit for each 
light sensor supported by the DMS, but shall not contain more than seven bits 
that are not associated with any light sensor. 
Each bit corresponds to an entry in the dmsLightSensorStatusTable. The low 
order bit corresponds to the light sensor with dmsLightSensorIndex = 1.
<Superseded by> ISO26048-1-Srsa:fdSrsaTypeWarning.FAL
<Informative> This object was deprecated in NTCIP 1203 v04 and replaced with 
the more universal SRSA object.
<Parameter Type> Status
<Object Identifier> 1.3.6.1.4.1.1206.4.2.3.9.7.28"
::= { statError 28 }

-- 5.11.2.7.2	Number of Rows in Light Sensor Status Table Parameter 
dmsLightSensorNumRows  OBJECT-TYPE 
SYNTAX      Integer32 (0..16)
UNITS       "rows" 
MAX-ACCESS  read-only 
STATUS      deprecated  
DESCRIPTION  
"<Definition> Indicates the number of rows in the dmsLightSensorStatusTable.
<Superseded by> ISO26048-1-Srsa:fdSrsaTypeCount.FAL
<Informative> This object was deprecated in NTCIP 1203 v04 and replaced with 
the more universal SRSA object.
<Parameter Type> Status
<Object Identifier> 1.3.6.1.4.1.1206.4.2.3.9.7.29"
::= { statError 29 }

-- 5.11.2.7.3	Light Sensor Status Table Parameter 
dmsLightSensorStatusTable  OBJECT-TYPE 
SYNTAX      SEQUENCE OF DmsLightSensorStatusEntry
MAX-ACCESS  not-accessible
STATUS      deprecated
DESCRIPTION "<Definition> A table containing status information for each 
light sensor within a DMS.
<Table Type> static
<Superseded by> ISO26048-1-Srsa:fdSrsaPortTable.FAL
<Informative> This object was deprecated in NTCIP 1203 v04 and replaced with 
the more universal SRSA object.
<Object Identifier> 1.3.6.1.4.1.1206.4.2.3.9.7.30"
::= {statError 30}

dmsLightSensorStatusEntry OBJECT-TYPE
SYNTAX      DmsLightSensorStatusEntry
MAX-ACCESS  not-accessible
STATUS      deprecated
DESCRIPTION "<Definition> An entry in the light sensor status table.
<Superseded by> ISO26048-1-Srsa:fdSrsaPortEntry.FAL
<Informative> This object was deprecated in NTCIP 1203 v04 and replaced with 
the more universal SRSA object."
INDEX { dmsLightSensorIndex }
::= {dmsLightSensorStatusTable 1}

DmsLightSensorStatusEntry ::= SEQUENCE {
   dmsLightSensorIndex          Integer32,
   dmsLightSensorDescription    DisplayString,
   dmsLightSensorCurrentReading Integer32,
   dmsLightSensorStatus         INTEGER } 

-- 5.11.2.7.3.1	Light Sensor Index Parameter 
dmsLightSensorIndex  OBJECT-TYPE 
SYNTAX      Integer32 (1..16) 
MAX-ACCESS  read-only 
STATUS      deprecated  
DESCRIPTION  
"<Definition> Index of the light sensor status table. This index corresponds 
to the bit position within the dmsLightSensorStatusMap bitmap: the row with 
index 1 corresponds to the low-order bit of the dmsLightSensorStatusMap, etc.
<Superseded by> ISO26048-1-Srsa:fdSrsaPortIndex.FAL
<Informative> This object was deprecated in NTCIP 1203 v04 and replaced with 
the more universal SRSA object.
<Parameter Type> Status
<Object Identifier> 1.3.6.1.4.1.1206.4.2.3.9.7.30.1.1"
::= { dmsLightSensorStatusEntry 1 }

-- 5.11.2.7.3.2	Light Sensor Description Parameter 
dmsLightSensorDescription  OBJECT-TYPE 
SYNTAX      DisplayString (SIZE (0..64)) 
MAX-ACCESS  read-only 
STATUS      deprecated  
DESCRIPTION  
"<Definition> Human-readable description of the light sensor. This value 
should provide enough information for maintenance personnel to identify the 
physical location of the light sensor within the DMS. The description shall 
include a meaningful definition of the location where the sensor defined in 
this row is located within the DMS.
<Superseded by> ISO26048-1-Srsa:fdSrsaPortDescription.FAL
<Informative> This object was deprecated in NTCIP 1203 v04 and replaced with 
the more universal SRSA object.
<Parameter Type> Status
<Object Identifier> 1.3.6.1.4.1.1206.4.2.3.9.7.30.1.2"
::= { dmsLightSensorStatusEntry 2 }

-- 5.11.2.7.3.3	Light Sensor Current Reading Parameter 
dmsLightSensorCurrentReading  OBJECT-TYPE 
SYNTAX      Integer32 (0..65535) 
MAX-ACCESS  read-only 
STATUS      deprecated  
DESCRIPTION  
"<Definition> Indicates the current reading of the light sensor. Total 
darkness shall cause the current reading to be zero, and full sunlight shall 
cause a reading of 65535. The light sensor reading shall be a linear 
function; the DMS must perform any required scaling.
<Superseded by> ISO26048-1-Srsa:fdSrsaPortValue.FAL
<Informative> This object was deprecated in NTCIP 1203 v04 and replaced with 
the more universal SRSA object.
<Parameter Type> Status
<Object Identifier> 1.3.6.1.4.1.1206.4.2.3.9.7.30.1.3"
::= { dmsLightSensorStatusEntry 3 }

-- 5.11.2.7.3.4	Light Sensor Status Parameter 
dmsLightSensorStatus  OBJECT-TYPE 
SYNTAX      INTEGER {
                 other (1), -- deprecated 
                 noError (2),
                 fail (3) } 
MAX-ACCESS  read-only 
STATUS      deprecated  
DESCRIPTION  
"<Definition> Indicates the current status of the indicated light sensor.
<Superseded by> ISO26048-1-Srsa:fdSrsaPortStatus.FAL
<Informative> This object was deprecated in NTCIP 1203 v04 and replaced with 
the more universal SRSA object.
<Parameter Type> Status
<Object Identifier> 1.3.6.1.4.1.1206.4.2.3.9.7.30.1.4"
::= { dmsLightSensorStatusEntry 4 }

-- 5.11.2.8	Humidity Data 

-- 5.11.2.8.1	Humidity Sensor Status Map Parameter 
dmsHumiditySensorStatusMap  OBJECT-TYPE 
SYNTAX      OCTET STRING (SIZE (0..2)) 
MAX-ACCESS  read-only 
STATUS      deprecated  
DESCRIPTION  
"<Definition> Indicates the operational status of all humidity sensors. If a 
humidity sensor is failed, the bit corresponding to the humidity sensor is 
set to 1; otherwise 0.  The size of this object shall always present one bit 
for each humidity sensor supported by the DMS, but shall not contain more 
than seven bits that are not associated with any humidity sensor. 
Each bit corresponds to an entry in the dmsHumiditySensorStatusTable. The low 
order bit corresponds to the humidity sensor with dmsHumiditySensorIndex = 1.
<Superseded by> ISO26048-1-Srsa:fdSrsaTypeWarning.FAH and FEH
<Informative> This object was deprecated in NTCIP 1203 v04 and replaced with 
the more universal SRSA object. The new design distinguishes between ambient 
humidity and enclosure humidity.
<Parameter Type> Status
<Object Identifier> 1.3.6.1.4.1.1206.4.2.3.9.7.31"
::= { statError 31 }

-- 5.11.2.8.2	Number of Rows in Humidity Sensor Status Table Parameter 
dmsHumiditySensorNumRows  OBJECT-TYPE 
SYNTAX      Integer32 (0..16)
UNITS       "rows" 
MAX-ACCESS  read-only 
STATUS      deprecated  
DESCRIPTION  
"<Definition> Indicates the number of rows in the 
dmsHumiditySensorStatusTable. 
<Superseded by> ISO26048-1-Srsa:fdSrsaTypeCount.FAH and FEH
<Informative> This object was deprecated in NTCIP 1203 v04 and replaced with 
the more universal SRSA object. The new design distinguishes between ambient 
humidity and enclosure humidity.
<Parameter Type> Status
<Object Identifier> 1.3.6.1.4.1.1206.4.2.3.9.7.32"
::= { statError 32 }

-- 5.11.2.8.3	Humidity Sensor Status Table Parameter 
dmsHumiditySensorStatusTable  OBJECT-TYPE 
SYNTAX      SEQUENCE OF DmsHumiditySensorStatusEntry
MAX-ACCESS  not-accessible
STATUS      deprecated
DESCRIPTION "<Definition> A table containing status information for each 
humidity sensor within a DMS.
<Table Type> static
<Superseded by> ISO26048-1-Srsa:fdSrsaPortTable.FAH and FEH
<Informative> This object was deprecated in NTCIP 1203 v04 and replaced with 
the more universal SRSA object. The new design distinguishes between ambient 
humidity and enclosure humidity.
<Object Identifier> 1.3.6.1.4.1.1206.4.2.3.9.7.33"
::= {statError 33}

dmsHumiditySensorStatusEntry OBJECT-TYPE
SYNTAX      DmsHumiditySensorStatusEntry
MAX-ACCESS  not-accessible
STATUS      deprecated
DESCRIPTION "<Definition> An entry in the humidity sensor status table.
<Superseded by> ISO26048-1-Srsa:fdSrsaPortEntry.FAH and FEH
<Informative> This object was deprecated in NTCIP 1203 v04 and replaced with 
the more universal SRSA object. The new design distinguishes between ambient 
humidity and enclosure humidity."
INDEX { dmsHumiditySensorIndex }
::= { dmsHumiditySensorStatusTable 1}

DmsHumiditySensorStatusEntry ::= SEQUENCE {
   dmsHumiditySensorIndex          Integer32,
   dmsHumiditySensorDescription    DisplayString,
   dmsHumiditySensorCurrentReading Integer32,
   dmsHumiditySensorStatus         INTEGER } 

-- 5.11.2.8.3.1	Humidity Sensor Index Parameter 
dmsHumiditySensorIndex  OBJECT-TYPE 
SYNTAX      Integer32 (1..16) 
MAX-ACCESS  read-only 
STATUS      deprecated  
DESCRIPTION  
"<Definition> Index of the humidity sensor status table. This index 
corresponds to the bit position within the dmsHumiditySensorStatusMap bitmap: 
the row with index 1 corresponds to the low-order bit of the 
dmsHumiditySensorStatusMap, etc. 
<Superseded by> ISO26048-1-Srsa:fdSrsaPortIndex.FAH and FEH
<Informative> This object was deprecated in NTCIP 1203 v04 and replaced with 
the more universal SRSA object. The new design distinguishes between ambient 
humidity and enclosure humidity.
<Parameter Type> Status
<Object Identifier> 1.3.6.1.4.1.1206.4.2.3.9.7.33.1.1"
::= { dmsHumiditySensorStatusEntry 1 }

-- 5.11.2.8.3.2	Humidity Sensor Description Parameter 
dmsHumiditySensorDescription  OBJECT-TYPE 
SYNTAX      DisplayString (SIZE (0..64)) 
MAX-ACCESS  read-only 
STATUS      deprecated  
DESCRIPTION  
"<Definition> Human-readable description of the humidity sensor. This value 
should provide enough information for maintenance personnel to identify the 
physical location of the humidity sensor within the DMS. The description 
shall include a meaningful definition of the location where the sensor 
defined in this row is located within the DMS.
<Superseded by> ISO26048-1-Srsa:fdSrsaPortDescription.FAH and FEH
<Informative> This object was deprecated in NTCIP 1203 v04 and replaced with 
the more universal SRSA object. The new design distinguishes between ambient 
humidity and enclosure humidity.
<Parameter Type> Status
<Object Identifier> 1.3.6.1.4.1.1206.4.2.3.9.7.33.1.2"
::= { dmsHumiditySensorStatusEntry 2 }

-- 5.11.2.8.3.3	Humidity Sensor Current Reading Parameter 
dmsHumiditySensorCurrentReading  OBJECT-TYPE 
SYNTAX      Integer32 (0..100)
UNITS       "percent relative humidity" 
MAX-ACCESS  read-only 
STATUS      deprecated  
DESCRIPTION  
"<Definition> Indicates the current reading of the humidity sensor, in 
percent relative humidity.
<Superseded by> ISO26048-1-Srsa:fdSrsaPortValue.FAH and FEH
<Informative> This object was deprecated in NTCIP 1203 v04 and replaced with 
the more universal SRSA object. The new design distinguishes between ambient 
humidity and enclosure humidity.
<Parameter Type> Status
<Object Identifier> 1.3.6.1.4.1.1206.4.2.3.9.7.33.1.3"
::= { dmsHumiditySensorStatusEntry 3 }

-- 5.11.2.8.3.4	Humidity Sensor Status Parameter 
dmsHumiditySensorStatus  OBJECT-TYPE 
SYNTAX      INTEGER {
                 other (1), -- deprecated 
                 noError (2),
                 fail (3) } 
MAX-ACCESS  read-only 
STATUS      deprecated  
DESCRIPTION  
"<Definition> Indicates the current status of the indicated humidity sensor.
<Superseded by> ISO26048-1-Srsa:fdSrsaPortStatus.FAH and FEH
<Informative> This object was deprecated in NTCIP 1203 v04 and replaced with 
the more universal SRSA object. The new design distinguishes between ambient 
humidity and enclosure humidity.
<Parameter Type> Status
<Object Identifier> 1.3.6.1.4.1.1206.4.2.3.9.7.33.1.4"
::= { dmsHumiditySensorStatusEntry 4 }

-- 5.11.2.9	Temperature Sensor Data 

-- 5.11.2.9.1	Temperature Sensor Status Map Parameter
dmsTempSensorStatusMap  OBJECT-TYPE 
SYNTAX      OCTET STRING (SIZE (0..2)) 
MAX-ACCESS  read-only 
STATUS      deprecated  
DESCRIPTION  
"<Definition> Indicates the operational status of all temperature sensors. If 
a temperature sensor is failed, the bit corresponding to the temperature 
sensor is set to 1; otherwise 0. The size of this object shall always present 
one bit for each temperature sensor supported by the DMS, but shall not 
contain more than seven bits that are not associated with any temperature 
sensor. 

Each bit corresponds to an entry in the dmsTempSensorStatusTable. The low 
order bit corresponds to the temperature sensor with dmsTempSensorIndex = 1.
<Superseded by> ISO26048-1-Srsa:fdSrsaTypeWarning.FAT and FET
<Informative> This object was deprecated in NTCIP 1203 v04 and replaced with 
the more universal SRSA object. The new design distinguishes between ambient 
temperature and enclosure temperature.
<Parameter Type> Status
<Object Identifier> 1.3.6.1.4.1.1206.4.2.3.9.7.34"
::= { statError 34 }

-- 5.11.2.9.2	Number of Rows in Temperature Sensor Status Table Parameter 
dmsTempSensorNumRows  OBJECT-TYPE 
SYNTAX      Integer32 (0..16)
UNITS       "rows" 
MAX-ACCESS  read-only 
STATUS      deprecated  
DESCRIPTION  
"<Definition> Indicates the number of rows in the dmsTempSensorStatusTable.
<Superseded by> ISO26048-1-Srsa:fdSrsaTypeCount.FAT and FET
<Informative> This object was deprecated in NTCIP 1203 v04 and replaced with 
the more universal SRSA object. The new design distinguishes between ambient 
temperature and enclosure temperature.
<Parameter Type> Status
<Object Identifier> 1.3.6.1.4.1.1206.4.2.3.9.7.35"
::= { statError 35 }

-- 5.11.2.9.3	Temperature Sensor Status Table Parameter 
dmsTempSensorStatusTable  OBJECT-TYPE 
SYNTAX      SEQUENCE OF DmsTempSensorStatusEntry
MAX-ACCESS  not-accessible
STATUS      deprecated
DESCRIPTION "<Definition> A table containing status information for each 
temperature sensor within a DMS.
<Table Type> static
<Superseded by> ISO26048-1-Srsa:fdSrsaPortTable.FAT and FET
<Informative> This object was deprecated in NTCIP 1203 v04 and replaced with 
the more universal SRSA object. The new design distinguishes between ambient 
temperature and enclosure temperature.
<Object Identifier> 1.3.6.1.4.1.1206.4.2.3.9.7.36"
::= {statError 36}

dmsTempSensorStatusEntry OBJECT-TYPE
SYNTAX      DmsTempSensorStatusEntry
MAX-ACCESS  not-accessible
STATUS      deprecated
DESCRIPTION "<Definition> An entry in the temperature sensor status table.
<Superseded by> ISO26048-1-Srsa:fdSrsaPortEntry.FAT and FET
<Informative> This object was deprecated in NTCIP 1203 v04 and replaced with 
the more universal SRSA object. The new design distinguishes between ambient 
temperature and enclosure temperature."
INDEX { dmsTempSensorIndex }
::= { dmsTempSensorStatusTable 1}

DmsTempSensorStatusEntry ::= SEQUENCE {
   dmsTempSensorIndex                   Integer32,
   dmsTempSensorDescription             DisplayString,
   dmsTempSensorCurrentReading          ITSInteger8,
   dmsTempSensorHighWarningTemperature  ITSInteger8,
   dmsTempSensorLowWarningTemperature   ITSInteger8,
   dmsTempSensorHighCriticalTemperature ITSInteger8,
   dmsTempSensorLowCriticalTemperature  ITSInteger8,
   dmsTempSensorStatus                  INTEGER } 

-- 5.11.2.9.3.1	Temperature Sensor Index Parameter 
dmsTempSensorIndex  OBJECT-TYPE 
SYNTAX      Integer32 (1..16) 
MAX-ACCESS  read-only 
STATUS      deprecated  
DESCRIPTION  
"<Definition> Index of the temperature sensor status table. This index 
corresponds to the bit position within the dmsTempSensorStatusMap bitmap: the 
row with index 1 corresponds to the low-order bit of the 
dmsTempSensorStatusMap, etc.
<Superseded by> ISO26048-1-Srsa:fdSrsaPortIndex.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.1"
::= { dmsTempSensorStatusEntry 1 }

-- 5.11.2.9.3.2	Temperature Sensor Description Parameter 
dmsTempSensorDescription  OBJECT-TYPE 
SYNTAX      DisplayString (SIZE (0..64)) 
MAX-ACCESS  read-only 
STATUS      deprecated  
DESCRIPTION  
"<Definition> Human-readable description of the temperature sensor. This 
value should provide enough information for maintenance personnel to identify 
the physical location of the temperature sensor within the DMS.
<Superseded by> ISO26048-1-Srsa:fdSrsaPortDescription.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.2"
::= { dmsTempSensorStatusEntry 2 }

-- 5.11.2.9.3.3	Temperature Sensor Current Reading Parameter 
dmsTempSensorCurrentReading  OBJECT-TYPE 
SYNTAX      ITSInteger8
UNITS       "degrees Celsius" 
MAX-ACCESS  read-only 
STATUS      deprecated  
DESCRIPTION  
"<Definition> Indicates the current reading of the temperature sensor in full 
degrees Celsius.
<Superseded by> ISO26048-1-Srsa:fdSrsaPortValue.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.3"
::= { dmsTempSensorStatusEntry 3 }

-- 5.11.2.9.3.4	Temperature Sensor High Warning Temperature Parameter 
dmsTempSensorHighWarningTemperature  OBJECT-TYPE 
SYNTAX      ITSInteger8 
UNITS       "degrees Celsius" 
MAX-ACCESS  read-only 
STATUS      deprecated  
DESCRIPTION  
"<Definition> Indicates the high value of the temperature associated with 
this temperature sensor that generates a warning, in full degrees Celsius. 
This value should not be lower than the value of the 
dmsTempSensorLowWarningTemperature object.
<Superseded by> ISO26048-1-Srsa:fdSrsaPortMaxThreshold.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.4"
::= { dmsTempSensorStatusEntry 4 }

-- 5.11.2.9.3.5	Temperature Sensor Low Warning Temperature Parameter
dmsTempSensorLowWarningTemperature  OBJECT-TYPE 
SYNTAX      ITSInteger8  
UNITS       "degrees Celsius" 
MAX-ACCESS  read-only 
STATUS      deprecated  
DESCRIPTION  
"<Definition> Indicates the low value of the temperature associated with this 
temperature sensor that generates a warning, in full degrees Celsius. This 
value should not be higher than the value of the 
dmsTempSensorHighWarningTemperature object.
<Superseded by> ISO26048-1-Srsa:fdSrsaPortMinThreshold.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.5"
::= { dmsTempSensorStatusEntry 5 }

-- 5.11.2.9.3.6	Temperature Sensor High Critical Temperature Parameter 
dmsTempSensorHighCriticalTemperature  OBJECT-TYPE 
SYNTAX      ITSInteger8  
UNITS       "degrees Celsius" 
MAX-ACCESS  read-only 
STATUS      deprecated  
DESCRIPTION  
"<Definition> Indicates the high value of the critical temperature associated 
with this temperature sensor, in full degrees Celsius. This value shall not 
be lower than the value of the dmsTempSensorLowCriticalTemperature object.
<Superseded by> ISO26048-1-CondTrigger:fdCondTriggerValue where 
fdCondTriggerActionGroup calls an entry that includes 
dmsCallableSignDisplayShutdown.
<Informative> This object was deprecated in NTCIP 1203 v04 and replaced with 
the more universal SRSA object. The new design distinguishes between ambient 
temperature and enclosure temperature.
<Parameter Type> Status
<Object Identifier> 1.3.6.1.4.1.1206.4.2.3.9.7.36.1.6"
::= { dmsTempSensorStatusEntry 6 }

-- 5.11.2.9.3.7	Temperature Sensor Low Critical Temperature Parameter
dmsTempSensorLowCriticalTemperature  OBJECT-TYPE 
SYNTAX      ITSInteger8  
UNITS       "degrees Celsius" 
MAX-ACCESS  read-only 
STATUS      deprecated  
DESCRIPTION  
"<Definition> Indicates the low value of the critical temperature associated 
with this temperature sensor, in full degrees Celsius. This value shall not 
be higher than the value of the dmsTempSensorHighCriticalTemperature object.
<Superseded by> ISO26048-1-CondTrigger:fdCondTriggerValue2 where 
fdCondTriggerActionGroup2 calls an entry that includes 
dmsCallableSignDisplayRestart.
<Informative> This object was deprecated in NTCIP 1203 v04 and replaced with 
an entry in the Conditional Trigger Table that enables the functionality. 
<Parameter Type> Status
<Object Identifier> 1.3.6.1.4.1.1206.4.2.3.9.7.36.1.7"
::= { dmsTempSensorStatusEntry 7 }

-- 5.11.2.9.3.8	Temperature Sensor Status Parameter 
dmsTempSensorStatus  OBJECT-TYPE 
SYNTAX      INTEGER { 
              other (1),
              noError (2),
              fail (3) } 
MAX-ACCESS  read-only 
STATUS      deprecated  
DESCRIPTION  
"<Definition> Indicates the current status of the indicated temperature 
sensor.
<Superseded by> ISO26048-1-Srsa:fdSrsaPortStatus.FAT and FET
<Informative> This object was deprecated in NTCIP 1203 v04 and replaced with 
the more universal SRSA object. The new design distinguishes between ambient 
temperature and enclosure temperature.
<Parameter Type> Status
<Object Identifier> 1.3.6.1.4.1.1206.4.2.3.9.7.36.1.8"
::= { dmsTempSensorStatusEntry 8 }

-- 5.11.2.9.4	Temperature Sensor Highest Critical Temperature Parameter 
dmsTempSensorHighestCriticalTempThreshold  OBJECT-TYPE 
SYNTAX      ITSInteger8  
UNITS       "degrees Celsius" 
MAX-ACCESS  read-only 
STATUS      deprecated  
DESCRIPTION  
"<Definition> Indicates the highest value of the critical temperature 
threshold associated with any of the supported temperature sensors in the 
DMS, in full degrees Celsius. 
<Superseded by> ISO26048-1-Srsa:fdSrsaPortMaxValue.FET
<Parameter Type> Status
<Object Identifier> 1.3.6.1.4.1.1206.4.2.3.9.7.37"
::= { statError 37 }

-- 5.11.2.9.5	Temperature Sensor Lowest Critical Temperature Parameter 
dmsTempSensorLowestCriticalTempThreshold  OBJECT-TYPE 
SYNTAX      ITSInteger8  
UNITS       "degrees Celsius" 
MAX-ACCESS  read-only 
STATUS      deprecated  
DESCRIPTION  
"<Definition> Indicates the lowest value of the critical temperature 
threshold associated with any of the supported temperature sensors in the 
DMS, in full degrees Celsius. 
<Superseded by> ISO26048-1-Srsa:fdSrsaPortMinValue.FET 
<Parameter Type> Status
<Object Identifier> 1.3.6.1.4.1.1206.4.2.3.9.7.38"
::= { statError 38 }

-- 5.11.3	-Power Status Objects 
statPower  OBJECT-IDENTITY 
STATUS  deprecated
DESCRIPTION 
"<Definition> This node is an identifier used to group all objects supporting 
DMS sign power status monitoring functions that are common to DMS devices. 
<Object Identifier> 1.3.6.1.4.1.1206.4.2.3.9.8"
::= { dmsStatus 8 }

-- 5.11.3.1	Sign Volts Parameter 
signVolts  OBJECT-TYPE 
SYNTAX      Integer32 (0..65535)
UNITS       "hundredths of a volt" 
MAX-ACCESS  read-only 
STATUS      deprecated  
DESCRIPTION  
"<Definition> A voltage measurement in units of hundredth (1/100) of a volt. 
The maximum value (0xFFFF) corresponds to a voltage of 655.35 volts. This is 
an indication of the sign battery voltage.
<Superseded by> ISO26048-1-Srsa:fdSrsaPortValue.FBV
<Informative> This object was deprecated in NTCIP 1203 v04 and replaced with 
the more universal SRSA object.
<Parameter Type> Status
<Object Identifier> 1.3.6.1.4.1.1206.4.2.3.9.8.1"
::= { statPower 1 }

-- 5.11.3.2	Low Fuel Threshold Parameter 
lowFuelThreshold  OBJECT-TYPE 
SYNTAX      Integer32 (0..100)
UNITS       "percent" 
MAX-ACCESS  read-write 
STATUS      deprecated  
DESCRIPTION  
"<Definition> Indicates the low fuel level threshold used to alert the user. 
The threshold is indicated as a percent (%) of a full tank. When the level of 
fuel is below the threshold, the bit for power alarm (bit 2) in the 
shortErrorStatus-object shall be set to one (1).
<Superseded by> ISO26048-1-Srsa:fdSrsaPortMinThreshold.FGF
<Informative> This object was deprecated in NTCIP 1203 v04 and replaced with 
the more universal SRSA object.
<Parameter Type> Status
<Object Identifier> 1.3.6.1.4.1.1206.4.2.3.9.8.2"
::= { statPower 2 }

-- 5.11.3.3	Fuel Level Parameter 
fuelLevel  OBJECT-TYPE 
SYNTAX      Integer32 (0..100)
UNITS       "percent" 
MAX-ACCESS  read-only 
STATUS      deprecated  
DESCRIPTION  
"<Definition> A number indicating the amount of fuel remaining, specified as 
a percent (%) of a full tank. 
<Superseded by> ISO26048-1-Srsa:fdSrsaPortValue.FGF
<Informative> This object was deprecated in NTCIP 1203 v04 and replaced with 
the more universal SRSA object.
<Parameter Type> Status
<Object Identifier> 1.3.6.1.4.1.1206.4.2.3.9.8.3"
::= { statPower 3 }

-- 5.11.3.4	Engine RPM Parameter 
engineRPM  OBJECT-TYPE 
SYNTAX      Integer32 (0..255)
UNITS       "rpm" 
MAX-ACCESS  read-only 
STATUS      deprecated  
DESCRIPTION  
"<Definition> Indicates the engine rpm in units of 100. This provides a range 
from 0 rpm to 25500 rpm.
<Superseded by> ISO26048-1-Srsa:fdSrsaPortValue.FGS
<Informative> This object was deprecated in NTCIP 1203 v04 and replaced with 
the more universal SRSA object.
<Parameter Type> Status
<Object Identifier> 1.3.6.1.4.1.1206.4.2.3.9.8.4"
::= { statPower 4 }

-- 5.11.3.5	Line Volts Parameter 
lineVolts  OBJECT-TYPE 
SYNTAX      Integer32 (0..255) 
UNITS       "volts"
MAX-ACCESS  read-only 
STATUS      deprecated  
DESCRIPTION  
"<Definition> The DMS line voltage measurement in (1.0) volts. The range is 0 
volts to 255 volts.
<Superseded by> ISO26048-1-Srsa:fdSrsaPortValue.FLV
<Informative> This object was deprecated in NTCIP 1203 v04 and replaced with 
the more universal SRSA object.
<Parameter Type> Status
<Object Identifier> 1.3.6.1.4.1.1206.4.2.3.9.8.5"
::= { statPower 5 }

-- 5.11.3.6	Power Source Parameter 
powerSource  OBJECT-TYPE 
SYNTAX      INTEGER {
                 other (1),
                 powerShutdown (2),
                 noSignPower (3),
                 acLine (4),
                 generator (5),
                 solar (6),
                 batteryUPS (7) } 
MAX-ACCESS  read-only 
STATUS      deprecated  
DESCRIPTION  
"<Definition> Indicates the source of power that is currently utilized by the 
sign.
<Format>
  other: indicates that the sign is powered by a method not listed 
     below (see device manual);
  powerShutdown: indicates that there is just enough power to perform 
     shutdown activities.
  noSignPower: indicates that the sign controller has power but the 
     sign display has no power;
  acLine: indicates that the controller and sign is powered by AC 
     power;
  generator: indicates that the sign and the controller are powered by 
     a generator; 
  solar: indicates that the sign and the controller are powered by solar 
     equipment; 
  battery-UPS: indicates that the sign and controller are powered by 
     battery or UPS with no significant charging occurring.
<Superseded by> ISO26048-1-Srsa: fdPowerSource
<Informative> This object was deprecated in NTCIP 1203 v04 and replaced with 
the more universal object from ISO 26048-1.
<Parameter Type> Status
<Object Identifier> 1.3.6.1.4.1.1206.4.2.3.9.8.6"
::= { statPower 6 }

-- 5.11.4	Temperature Status Objects 
statTemp  OBJECT-IDENTITY 
STATUS  deprecated
DESCRIPTION
"<Definition> This node is an identifier used to group all objects supporting 
DMS sign temperature status monitoring functions that are common to DMS 
devices. 
<Object Identifier> 1.3.6.1.4.1.1206.4.2.3.9.9"
::= { dmsStatus 9 }

-- 5.11.4.1	Minimum Temperature of Control Cabinet Parameter 
tempMinCtrlCabinet  OBJECT-TYPE 
SYNTAX      ITSInteger8 
UNITS       "degrees Celsius"
MAX-ACCESS  read-only 
STATUS      deprecated  
DESCRIPTION  
"<Definition> Indicates the current temperature (single sensor) or the 
current minimum temperature (multiple sensors) within the DMS Control Cabinet 
in degrees Celsius. 
<Superseded by> ISO26048-1-Srsa:fdSrsaTypeValueStatsMin.FET
<Informative> This object was deprecated in NTCIP 1203 v04 and replaced with 
the more universal object from ISO 26048-1. The new object combines sign 
housing and the control cabinet into a single value.
<Parameter Type> Status
<Object Identifier> 1.3.6.1.4.1.1206.4.2.3.9.9.1"
::= { statTemp 1 }

-- 5.11.4.2	Maximum Temperature of Control Cabinet Parameter 
tempMaxCtrlCabinet  OBJECT-TYPE 
SYNTAX      ITSInteger8 
UNITS       "degrees Celsius"
MAX-ACCESS  read-only 
STATUS      deprecated  
DESCRIPTION  
"<Definition> Indicates the current temperature (single sensor) or the 
current maximum temperature (multiple sensors) within the DMS Control Cabinet 
in degrees Celsius.
<Superseded by> ISO26048-1-Srsa:fdSrsaTypeValueStatsMax.FET
<Informative> This object was deprecated in NTCIP 1203 v04 and replaced with 
the more universal object from ISO 26048-1. The new object combines sign 
housing and the control cabinet into a single value.
<Parameter Type> Status
<Object Identifier> 1.3.6.1.4.1.1206.4.2.3.9.9.2"
::= { statTemp 2 }

-- 5.11.4.3	Minimum Ambient Temperature Parameter 
tempMinAmbient  OBJECT-TYPE 
SYNTAX      ITSInteger8 
UNITS       "degrees Celsius"
MAX-ACCESS  read-only 
STATUS      deprecated  
DESCRIPTION  
"<Definition> Indicates the current outside ambient temperature (single 
sensor) or the current minimum outside ambient temperature (multiple sensors) 
in degrees Celsius.
<Superseded by> ISO26048-1-Srsa:fdSrsaTypeValueStatsMin.FAT
<Informative> This object was deprecated in NTCIP 1203 v04 and replaced with 
the more universal object from ISO 26048-1.
<Object Identifier> 1.3.6.1.4.1.1206.4.2.3.9.9.3"
::= { statTemp 3 }

-- 5.11.4.4	Maximum Ambient Temperature Parameter 
tempMaxAmbient  OBJECT-TYPE 
SYNTAX      ITSInteger8 
UNITS       "degrees Celsius"
MAX-ACCESS  read-only 
STATUS      deprecated  
DESCRIPTION  
"<Definition> Indicates the current outside ambient temperature (single 
sensor) or the current maximum outside ambient temperature (multiple sensors) 
in degrees Celsius.
<Superseded by> ISO26048-1-Srsa:fdSrsaTypeValueStatsMax.FAT
<Informative> This object was deprecated in NTCIP 1203 v04 and replaced with 
the more universal object from ISO 26048-1.
<Parameter Type> Status
<Object Identifier> 1.3.6.1.4.1.1206.4.2.3.9.9.4"
::= { statTemp 4 }

-- 5.11.4.5	Minimum Temperature of Sign Housing Parameter 
tempMinSignHousing  OBJECT-TYPE 
SYNTAX      ITSInteger8 
UNITS       "degrees Celsius"
MAX-ACCESS  read-only 
STATUS      deprecated  
DESCRIPTION  
"<Definition> Indicates the current temperature (single sensor) or the 
current minimum temperature (multiple sensors) in the sign housing in degrees 
Celsius.
<Superseded by> ISO26048-1-Srsa:fdSrsaTypeValueStatsMin.FET
<Informative> This object was deprecated in NTCIP 1203 v04 and replaced with 
the more universal object from ISO 26048-1. The new object combines sign 
housing and the control cabinet into a single value.
<Parameter Type> Status
<Object Identifier> 1.3.6.1.4.1.1206.4.2.3.9.9.5"
::= { statTemp 5 }

-- 5.11.4.6	Maximum Temperature of Sign Housing Parameter 
tempMaxSignHousing  OBJECT-TYPE 
SYNTAX      ITSInteger8 
UNITS       "degrees Celsius"
MAX-ACCESS  read-only 
STATUS      deprecated  
DESCRIPTION  
"<Definition> Indicates the current temperature (single sensor) or the 
current maximum temperature (multiple sensors) in the sign housing in degrees 
Celsius.
<Superseded by> ISO26048-1-Srsa:fdSrsaTypeValueStatsMax.FET
<Informative> This object was deprecated in NTCIP 1203 v04 and replaced with 
the more universal object from ISO 26048-1. The new object combines sign 
housing and the control cabinet into a single value.
<Parameter Type> Status
<Object Identifier> 1.3.6.1.4.1.1206.4.2.3.9.9.6"
::= { statTemp 6 }

-- 5.11.4.7	Temperature Sensor Warning Parameter 
tempSensorWarningMap  OBJECT-TYPE 
SYNTAX      OCTET STRING (SIZE (0..2)) 
MAX-ACCESS  read-only 
STATUS      deprecated  
DESCRIPTION  
"<Definition> Indicates whether each temperature sensor has exceeded a 
dmsTempSensorHighWarningTemperature or dmsTempSensorLowWarningTemperature 
value. If a temperature sensor has exceeded the defined value, the bit 
corresponding to the temperature sensor is set to 1; otherwise 0. The mapping 
of bits to individual sensors is manufacturer specific. This bitmap of this 
object shall be configured as defined in the dmsTempSensorStatusTable in that 
the first bit of this object shall correspond to the first row in that table, 
the second bit shall correspond to the second row, and so forth.
<Superseded by> ISO26048-1-Srsa:fdSrsaTypeWarning.FET
<Informative> This object was deprecated in NTCIP 1203 v04 and replaced with 
the more universal object from ISO 26048-1.
<Parameter Type> Status
<Object Identifier> 1.3.6.1.4.1.1206.4.2.3.9.9.7"
::= { statTemp 7 }

-- 5.11.4.8	Critical Temperature Map Parameter 
tempSensorCriticalTempMap  OBJECT-TYPE 
SYNTAX      OCTET STRING (SIZE (0..2)) 
MAX-ACCESS  read-only 
STATUS      deprecated  
DESCRIPTION  
"<Definition> Indicates whether each temperature sensor has exceeded the 
dmsTempSensorHighCriticalTemperature or the 
dmsTempSensorLowCriticalTemperature threshold. If a temperature sensor has 
exceeded the defined value, the bit corresponding to the temperature sensor 
is set to 1; otherwise 0. The mapping of bits to individual sensors is 
manufacturer specific. This bitmap of this object shall be configured as 
defined in the dmsTempSensorStatusTable in that the first bit of this object 
shall correspond to the first row in that table, the second bit shall 
correspond to the second row, and so forth.
<Superseded by> ISO26048-1-Srsa:fdSrsaTypeStatus.FET
<Informative> This object was deprecated in NTCIP 1203 v04 and replaced with 
the more universal object from ISO 26048-1.
<Parameter Type> Status
<Object Identifier> 1.3.6.1.4.1.1206.4.2.3.9.9.8"
::= { statTemp 8 }

-- 5.11.5	SRSA Extension Objects 
dmsSrsaExtensions  OBJECT-IDENTITY 
STATUS  current
DESCRIPTION
"<Definition> This node is an identifier used to group all DMS-specific 
extensions to the ISO 26048-1 SRSA table.. 
<Object Identifier> 1.3.6.1.4.1.1206.4.2.3.9.10"
::= { dmsStatus 10 }

-- 5.11.5.1	SRSA Pixels Table Parameter 
dmsSrsaPixelsTable  OBJECT-TYPE 
SYNTAX      SEQUENCE OF DmsSrsaPixelsEntry
MAX-ACCESS  not-accessible
STATUS      current
DESCRIPTION "<Definition> A table that extends the fdSrsaPortTable to 
identify the pixels associated with an entry in the SRSA table. 
<Informative> For example, if the SRSA entry is for lamp status, this table 
will indicate the pixels associated with the lamp. When the lamp experiences 
an error, the management station can determine the affected pixels.
One row shall exist in this table for each SRSA port with a type of 'MLS'. 
Rows may exist in this table for other items; for example, power supplies 
('FPS') can be associated with groups of pixels.
<Table Type> static
<Object Identifier> 1.3.6.1.4.1.1206.4.2.3.9.10.1"
::= { dmsSrsaExtensions 1}

dmsSrsaPixelsEntry  OBJECT-TYPE
SYNTAX      DmsSrsaPixelsEntry
MAX-ACCESS  not-accessible
STATUS      current
DESCRIPTION "<Definition> An entry in the lamp SRSA details table."
INDEX { fdSrsaTypeCode, fdSrsaPortIndex }
::= { dmsSrsaPixelsTable 1}

DmsSrsaPixelsEntry ::= SEQUENCE {
   dmsSrsaPixelsTop     Integer32,
   dmsSrsaPixelsLeft    Integer32,
   dmsSrsaPixelsBottom  Integer32,
   dmsSrsaPixelsRight   Integer32} 

-- 5.11.5.1.1	SRSA Top Pixel Parameter 
dmsSrsaPixelsTop  OBJECT-TYPE 
SYNTAX      Integer32 (1..65535) 
MAX-ACCESS  read-only 
STATUS      current 
DESCRIPTION  
"<Definition> Indicates the topmost row of pixels served by this entry. The 
top-most row on the sign face is row 1.
<Parameter Type> Status
<Object Identifier> 1.3.6.1.4.1.1206.4.2.3.9.10.1.1.1"
::= { dmsSrsaPixelsEntry 1 }

-- 5.11.5.1.2	SRSA Left Pixel Parameter 
dmsSrsaPixelsLeft  OBJECT-TYPE 
SYNTAX      Integer32 (1..65535) 
MAX-ACCESS  read-only 
STATUS      current 
DESCRIPTION  
"<Definition> Indicates the leftmost column of pixels served by this entry. 
The left-most column on the sign face is column 1.
<Parameter Type> Status
<Object Identifier> 1.3.6.1.4.1.1206.4.2.3.9.10.1.1.2"
::= { dmsSrsaPixelsEntry 2 }

-- 5.11.5.1.3	SRSA Bottom Pixel Parameter 
dmsSrsaPixelsBottom  OBJECT-TYPE 
SYNTAX      Integer32 (1..65535) 
MAX-ACCESS  read-only 
STATUS      current 
DESCRIPTION  
"<Definition> Indicates the bottommost row of pixels served by this entry. 
The top-most row on the sign face is row 1.
<Parameter Type> Status
<Object Identifier> 1.3.6.1.4.1.1206.4.2.3.9.10.1.1.3"
::= { dmsSrsaPixelsEntry 3 }

-- 5.11.5.1.4	SRSA Right Pixel Parameter 
dmsSrsaPixelsRight  OBJECT-TYPE 
SYNTAX      Integer32  
MAX-ACCESS  read-only 
STATUS      current 
DESCRIPTION  
"<Definition> Indicates the rightmost column of pixels served by this entry. 
The left-most column on the sign face is column 1.
<Parameter Type> Status
<Object Identifier> 1.3.6.1.4.1.1206.4.2.3.9.10.1.1.4"
::= { dmsSrsaPixelsEntry 4 }

-- 5.12	Graphic Definition Objects 
graphicDefinition  OBJECT-IDENTITY 
STATUS  current
DESCRIPTION
"<Definition> This node is an identifier used to group all objects for DMS 
graphic configurations that are common to DMS devices. 
<Object Identifier> 1.3.6.1.4.1.1206.4.2.3.10"
::= { dms 10 }


-- 5.12.1	Maximum Number of Graphics Parameter 
dmsGraphicMaxEntries  OBJECT-TYPE 
SYNTAX      Integer32 (0..255)
UNITS       "graphics" 
MAX-ACCESS  read-only 
STATUS      current  
DESCRIPTION  
"<Definition> Indicates the maximum number of graphics that the sign can 
store.
<Parameter Type> Status
<Object Identifier> 1.3.6.1.4.1.1206.4.2.3.10.1"
::= { graphicDefinition 1 }

-- 5.12.2	Number of Graphics Parameter 
dmsGraphicNumEntries  OBJECT-TYPE 
SYNTAX      Integer32 (0..255)
UNITS       "graphics" 
MAX-ACCESS  read-only 
STATUS      current  
DESCRIPTION  
"<Definition> Indicates the number of graphics currently stored within the 
sign.
<Parameter Type> Status
<Object Identifier> 1.3.6.1.4.1.1206.4.2.3.10.2"
::= { graphicDefinition 2 }

-- 5.12.3	Maximum Graphic Size Parameter 
dmsGraphicMaxSize  OBJECT-TYPE 
SYNTAX      Integer32 (0..65535)
UNITS       "octets" 
MAX-ACCESS  read-only 
STATUS      deprecated  
DESCRIPTION  
"<Definition> Indicates the maximum size (in bytes) of each graphic the sign 
is capable of storing. This value shall be an even multiple of the object 
dmsGraphicBlockSize.
<Parameter Type> Status
<Superseded by> dmsGraphicMaxSize4
<Informative> This object was deprecated in NTCIP 1203 v04 so that larger 
graphics could be supported.
<Object Identifier> 1.3.6.1.4.1.1206.4.2.3.10.3"
::= { graphicDefinition 3 }

-- 5.12.4	Available Graphic Memory Parameter
availableGraphicMemory  OBJECT-TYPE 
SYNTAX      Counter32
UNITS       "octets" 
MAX-ACCESS  read-only 
STATUS      deprecated  
DESCRIPTION  
"<Definition> An indication of the amount of memory left, in bytes, to store 
graphics.
<Superseded by> dmsAvailableGraphicMemoryV4
<Informative> This object was deprecated in NTCIP 1203 v04 because it does 
not fulfill the semantics of a 'Counter', which is more rigidly enforced in 
SNMPv3.
<Parameter Type> Status
<Object Identifier> 1.3.6.1.4.1.1206.4.2.3.10.4"
::= { graphicDefinition 4 }


-- 5.12.5	Graphic Block Size Parameter 
dmsGraphicBlockSize  OBJECT-TYPE 
SYNTAX      Integer32 (0..65535)
UNITS       "octets" 
MAX-ACCESS  read-only 
STATUS      current  
DESCRIPTION  
"<Definition> Indicates the size of each block within each graphic bitmap 
image. A graphic bitmap may consist of at most 
dmsGraphicMaxSize/dmsGraphicBlockSize number of blocks.
<Parameter Type> Status
<Object Identifier> 1.3.6.1.4.1.1206.4.2.3.10.5"
::= { graphicDefinition 5 }

-- 5.12.6	Graphics Table Parameter 
dmsGraphicTable  OBJECT-TYPE 
SYNTAX      SEQUENCE OF DmsGraphicEntry
MAX-ACCESS  not-accessible
STATUS      current 
DESCRIPTION "<Definition> A table containing the information needed to 
configure/define a particular graphic. The values of a columnar object 
(except the dmsGraphicStatus) cannot be changed when the 'dmsGraphicStatus'-
object of that particular row is any value other than 'modifying'.
<Table Type> static
<Object Identifier> 1.3.6.1.4.1.1206.4.2.3.10.6"
::= {graphicDefinition 6}

dmsGraphicEntry OBJECT-TYPE
SYNTAX      DmsGraphicEntry
MAX-ACCESS  not-accessible
STATUS      current 
DESCRIPTION "<Definition> Parameters of the Graphic Table."
INDEX {dmsGraphicIndex}
::= {dmsGraphicTable 1}

DmsGraphicEntry ::= SEQUENCE {
	dmsGraphicIndex	Integer32,
	dmsGraphicNumber	Integer32,
	dmsGraphicName	SnmpAdminString,
	dmsGraphicHeight	Integer32,
	dmsGraphicWidth	Integer32,
	dmsGraphicType	INTEGER,
	dmsGraphicID	Integer32, 
	dmsGraphicTransparentEnabled	Integer32,
	dmsGraphicTransparentColor	DmsColor,
	dmsGraphicStatus	INTEGER,
	dmsGraphicHeightV4	Integer32,
	dmsGraphicFilename	SnmpAdminString} 

-- 5.12.6.1	Graphic Index Parameter 
dmsGraphicIndex  OBJECT-TYPE 
SYNTAX      Integer32 (1..255) 
MAX-ACCESS  read-only 
STATUS      current  
DESCRIPTION  
"<Definition> Indicates the row number of the entry. This index directly 
corresponds to dmsGraphicBitmapIndex located in dmsGraphicBitmapTable. The 
storage for each graphic of this table is located in dmsGraphicBitmapTable.
<Parameter Type> Status
<Object Identifier> 1.3.6.1.4.1.1206.4.2.3.10.6.1"
::= { dmsGraphicEntry 1 }

-- 5.12.6.2	Graphic Number Parameter 
dmsGraphicNumber  OBJECT-TYPE 
SYNTAX      Integer32 (1..255) 
MAX-ACCESS  read-write 
STATUS      current  
DESCRIPTION  
"<Definition> A unique, user-specified number for a particular graphic which 
can be different from the value of the dmsGraphicIndex-object. This is the 
number referenced by MULTI when specifying a particular graphic. A device 
shall return a inconsistentValue error, if this value is not unique.
<Parameter Type> Configuration
<Object Identifier> 1.3.6.1.4.1.1206.4.2.3.10.6.2"
::= { dmsGraphicEntry 2 }

-- 5.12.6.3	Graphic Name Parameter 
dmsGraphicName  OBJECT-TYPE 
SYNTAX      SnmpAdminString (SIZE (0..64)) 
MAX-ACCESS  read-write 
STATUS      current  
DESCRIPTION  
"<Definition> Indicates the name of the graphic.
<Parameter Type> Configuration
<Object Identifier> 1.3.6.1.4.1.1206.4.2.3.10.6.3"
::= { dmsGraphicEntry 3 }

-- 5.12.6.4	Graphic Height Parameter 
dmsGraphicHeight  OBJECT-TYPE 
SYNTAX      Integer32 (1..255)
UNITS       "pixels" 
MAX-ACCESS  read-write 
STATUS      deprecated  
DESCRIPTION  
"<Definition> Indicates the height of the graphic in pixels. The value of 
this object shall not exceed vmsSignHeightPixels.
<Parameter Type> Configuration
<Superseded by> dmsGraphicHeightV4
<Informative> This object was deprecated in NTCIP 1203 v04 so that larger 
graphics could be supported.
<Object Identifier> 1.3.6.1.4.1.1206.4.2.3.10.6.4"
::= { dmsGraphicEntry 4 }

-- 5.12.6.5	Graphic Width Parameter 
dmsGraphicWidth  OBJECT-TYPE 
SYNTAX      Integer32 (1..65535)
UNITS       "pixels" 
MAX-ACCESS  read-write 
STATUS      current  
DESCRIPTION  
"<Definition> Indicates the width of the graphic in pixels. The value of this 
object shall not exceed vmsSignWidthPixels.
<Parameter Type> Configuration
<Object Identifier> 1.3.6.1.4.1.1206.4.2.3.10.6.5"
::= { dmsGraphicEntry 5 }

-- 5.12.6.6	Graphic Type Parameter 
dmsGraphicType  OBJECT-TYPE 
SYNTAX      DmsColorScheme  
MAX-ACCESS  read-write 
STATUS      current  
DESCRIPTION  
"<Definition> Indicates the type of the graphic stored in this row. 
For definitions of the values see the dmsColorScheme object.  All DMS shall 
support the monochrome1bit graphic type.
<Parameter Type> Configuration
<Object Identifier> 1.3.6.1.4.1.1206.4.2.3.10.6.6"
::= { dmsGraphicEntry 6 }

-- 5.12.6.7	Graphic ID Parameter 
dmsGraphicID  OBJECT-TYPE 
SYNTAX      Integer32 (0..65535) 
MAX-ACCESS  read-only 
STATUS      current  
DESCRIPTION  
"<Definition> Each graphic that has been downloaded to a sign shall have a 
relatively unique ID. This ID shall be calculated using the CRC-16 algorithm 
defined in ISO 3309 and the associated OER-encoded (as defined in ITU-T 
X.696) GraphicInfoList.

The following definitions are used to define the above referenced 
GraphicInfoList.

Complete definitions for these referenced objects, including size 
information, is contained elsewhere in this document.

GraphicInfoList ::= SEQUENCE {
        number INTEGER(1..255),
          -- dmsGraphicNumber of the subject graphic
        height INTEGER(1..65535),
          -- dmsGraphicHeightV4 of the subject graphic
        width INTEGER(1..65535),
          -- dmsGraphicWidth of the subject graphic
        type INTEGER (1..4),
          -- dmsGraphicType of the subject graphic
        transparentEnabled INTEGER(0..1) 
          -- dmsGraphicTransparentEnabled of the graphic
        transparentColor OCTET STRING (SIZE(3)) 
          -- dmsGraphicTransparentColor of the graphic if dmsGraphicType not 
          -- color24bit, first octet is the transparent color and remaining 
          -- octets are zero
        bitmap OCTET STRING (SIZE (Z))
          -- the bitmap of the subject graphic
        }

where   Z = ((height * width) + 7) / 8  -- for monochrome1bit 
                                        --(remaining bits are set to zero)
        Z = (height * width) -- for monochrome8bit or colorClassic
        Z = (height * width) * 3 -- for color24bit

This gives a predictable byte stream for the GraphicInfoList:
[number]             -- 1 octet
[height]             -- 2 octets, MSB first
[width]              -- 2 octets, MSB first
[type]               -- 1 octet
[transparentEnabled] -- 1 octet
[transparentcolor]   -- 3 octets (last 2 octets set to 0 if not color24bit)
[bitmap]             -- Z octets, according to height, width & color scheme

Examples: 
Given the 10x6 bitmap - 84 92 63 08 C2 48 A1 70 =
@OOOO@OO@O
O@OO@OO@@O
OO@@OOOO@O
OO@@OOOO@O
O@OO@OOO@O
@OOOO@O@@@
OOOO

1)   dmsGraphicNumber = 3
     dmsGraphicHeightV4 = 6
     dmsGraphicWidth = 10
     dmsGraphicType = 1
     dmsGraphicTransparentEnabled = 0
     dmsGraphicTransparentColor = 1 
     dmsGraphicBitmap = 84 92 63 08 C2 48 A1 70

GraphicInfoList = 03 00 06 00 0A 01 00 01 00 00 84 92 63 08 C2 48 A1 70
dmsGraphicID = 0xB95A

where                03 = dmsGraphicNumber
                  00 06 = dmsGraphicHeightV4
                  00 0A = dmsGraphicWidth
                     01 = dmsGraphicType (monochrome1bit)
                     00 = dmsGraphicTransparentEnabled
              01  00 00 = dmsGraphicTransparentColor
84 92 63 08 C2 48 A1 70 = dmsGraphicBitmap

2)   dmsGraphicNumber = 4
     dmsGraphicHeightV4 = 6
     dmsGraphicWidth = 10
     dmsGraphicType = 1
     dmsGraphicTransparentEnabled = 0
     dmsGraphicTransparentColor = 0
     dmsGraphicBitmap = 84 92 63 08 C2 48 A1 70

GraphicInfoList = 04 00 06 00 0A 01 00 00 00 00 84 92 63 08 C2 48 A1 70
dmsGraphicID = 0xBFF5

where                04 = dmsGraphicNumber
                  00 06 = dmsGraphicHeightV4
                  00 0A = dmsGraphicWidth
                     01 = dmsGraphicType (monochrome1bit)
                     00 = dmsGraphicTransparentEnabled
               00 00 00 = dmsGraphicTransparentColor
84 92 63 08 C2 48 A1 70 = dmsGraphicBitmap

3) A 4x4 pixel color classic graphic of the letter 'Z' in red 

     dmsGraphicNumber = 5
     dmsGraphicHeightV4 = 4
     dmsGraphicWidth = 4
     dmsGraphicType = 3 
     dmsGraphicTransparentEnabled = 1
     dmsGraphicTransparentColor = 7
     dmsGraphicBitmap = 01 01 01 01 07 07 01 07 07 01 07 07 01 01 01 01

GraphicInfoList = 05 00 04 00 04 03 01 07 00 00 01 01 01 01 07 07 01 07 07 01 
07 07 01 01 01 01
dmsGraphicID = 0x8FE0

where                05 = dmsGraphicNumber
                     00 04 = dmsGraphicHeightV4
                     00 04 = dmsGraphicWidth
                     03 = dmsGraphicType (colorClassic)
                     01 = dmsGraphicTransparentEnabled
                     07 00 00 = dmsGraphicTransparentColor (white)
01 01 01 01 07 07 01 07 07 01 07 07 01 01 01 01 = dmsGraphicBitmap

4) -- a 2x2 pixel square RGB graphic with green as the transparent color in 
the lower left pixel
     dmsGraphicNumber = 7
     dmsGraphicHeightV4 = 2
     dmsGraphicWidth = 2
     dmsGraphicType = 4
     dmsGraphicTransparentEnabled = 1
     dmsGraphicTransparentColor = 00 FF 00
     dmsGraphicBitmap = FFFFFF FF00FF 00FF00 FF00FF

GraphicInfoList = 07 00 02 00 02 04 01 00 FF 00 FFFFFF FF00FF 00FF00 FF00FF
dmsGraphicID = 0x078D

where                    07 = dmsGraphicNumber
                      00 02 = dmsGraphicHeightV4
                      00 02 = dmsGraphicWidth
                         04 = dmsGraphicType (color24bit)
                         01 = dmsGraphicTransparentEnabled
                   00 FF 00 = dmsGraphicTransparentColor (green)
FFFFFF FF00FF 00FF00 FF00FF = dmsGraphicBitmap

<Parameter Type> Status
<Object Identifier> 1.3.6.1.4.1.1206.4.2.3.10.6.7"
::= { dmsGraphicEntry 7 }

-- 5.12.6.8	Graphic Transparent Enabled Parameter 
dmsGraphicTransparentEnabled  OBJECT-TYPE 
SYNTAX      Integer32 (0..1) 
MAX-ACCESS  read-write 
STATUS      current  
DESCRIPTION  
"<Definition> Indicates whether the graphic contains a color that is 
considered transparent. A value of 0 means there is no transparent color.
<Parameter Type> Configuration
<Object Identifier> 1.3.6.1.4.1.1206.4.2.3.10.6.8"
::= { dmsGraphicEntry 8 }

-- 5.12.6.9	Graphic Transparent Color Parameter 
dmsGraphicTransparentColor  OBJECT-TYPE 
SYNTAX      DmsColor 
MAX-ACCESS  read-write 
STATUS      current  
DESCRIPTION  
"<Definition> If dmsGraphicTransparentEnabled indicates that the graphic 
contains a transparent color, this object specifies the color. All pixels in 
the graphic that exactly match this color shall be considered transparent 
such that when the graphic is displayed on the sign, those transparent pixels 
will be left at whatever color exists on the message beneath the graphic (or 
before the graphic is 'painted' onto the sign). The format of this color is 
defined by the DmsColor textual convention.
<Parameter Type> Configuration
<Object Identifier> 1.3.6.1.4.1.1206.4.2.3.10.6.9"
::= { dmsGraphicEntry 9 }

-- 5.12.6.10	Graphic Status Parameter 
dmsGraphicStatus  OBJECT-TYPE 
SYNTAX      INTEGER {
                 notUsed (1),
                 modifying (2),
                 calculatingID (3),
                 readyForUse (4),
                 inUse (5),
                 permanent (6),
                 modifyReq (7),
                 readyForUseReq (8),
                 notUsedReq (9),
                 processingGraphicFile (10),
                 graphicFileError (11),
                 graphicError (12) } 
MAX-ACCESS  read-write 
STATUS      current  
DESCRIPTION  
"<Definition> Indicates the current state of the graphic. This state-machine 
allows for defining a graphic, readying a graphic (making it usable by a 
message), and preventing its modification. See Section 4.3.2 for additional 
state-machine requirements.

If dmsGraphicStatus is set to a value of notUsedReq (9), as this state-
machine transitions to the state of notUsed (1) the device shall release all 
memory space allocated to that graphic bitmap.
<Parameter Type> Configuration
<Object Identifier> 1.3.6.1.4.1.1206.4.2.3.10.6.10"
::= { dmsGraphicEntry 10 }

-- 5.12.6.11	Graphic Height Parameter Version 4
dmsGraphicHeightV4  OBJECT-TYPE 
SYNTAX      Integer32 (1..65535)
UNITS       "pixels" 
MAX-ACCESS  read-write 
STATUS      current  
DESCRIPTION  
"<Definition> Indicates the height of the graphic in pixels. The value of 
this object shall not exceed vmsSignHeightPixels.
<Parameter Type> Configuration
<Object Identifier> 1.3.6.1.4.1.1206.4.2.3.10.6.11"
::= { dmsGraphicEntry 11 }

-- 5.12.6.12	Graphic Filename Parameter 
dmsGraphicFilename  OBJECT-TYPE 
SYNTAX      SnmpAdminString
MAX-ACCESS  read-write 
STATUS      current  
DESCRIPTION  
"<Definition> Indicates the name and extension of the graphic file to be used 
to define the graphic. A set to this object shall cause the dmsGraphicStatus 
to transition to processingGraphicFile and the associated logic of clause 
4.3.2.3 to apply. A set of this object in the same request as a request to 
set dmsGraphicHeight, dmsGraphicWidth, dmsGraphicType, dmsGraphicID, 
dmsGraphicTransparencyEnabled, dmsGraphicTransparencyColor, 
dmsGraphicHeightV4, or dmsGraphicBlockBitmap for the same dmsGrahaphic shall 
result in an inconsistentValue error.

At the present time, only png files are allowed and an attempt to set this 
object to a value with an extension other than '.png' (or no extension) shall 
return a wrongValue error. 
<Parameter Type> Configuration
<Object Identifier> 1.3.6.1.4.1.1206.4.2.3.10.6.12"
::= { dmsGraphicEntry 12 }

-- 5.12.7	Graphics Bitmap Table Parameter 
dmsGraphicBitmapTable  OBJECT-TYPE 
SYNTAX      SEQUENCE OF DmsGraphicBitmapEntry
MAX-ACCESS  not-accessible
STATUS      current 
DESCRIPTION "<Definition> A table containing the bitmap information for the 
graphic entries within the dmsGraphicTable. The values of a columnar object 
in this table cannot be changed when the 'dmsGraphicStatus' object of the 
corresponding row (row with the same index) in the dmsGraphicTable is any 
value other than 'modifying'.

The dmsGraphicBitmapTable permits a complete bitmap to be downloaded to a 
sign in pieces small enough to fit within a single SNMP SetRequest. Each 
dmsGraphicBlockSize-sized chunk within the bitmap is represented by a 
distinct row of the bitmap data Table; that is, the table is indexed by (1) 
the dmsGraphicIndex, and (2) the dmsGraphicBlockNumber of a particular data 
block within the graphic's data. Note that this mechanism is purely a 
piecewise transfer method layered atop the bitmap data; when all the blocks 
of a graphic image are downloaded, they must, as a group, conform to the 
format described below. For a particular value of dmsGraphicIndex, the bitmap 
defining the graphic image can be constructed in the following manner: 
Concatenate the rows of the dmsGraphicBitmapTable with the matching 
dmsGraphicIndex, in order of the dmsGraphicBlockNumber value, until the 
resultant OCTET STRING is large enough to contain the entire image as defined 
by the dmsGraphicHeightV4 and dmsGraphicWidth values for the dmsGraphicIndex 
in question.

The format of a complete bitmap is described here:
A complete bitmap image is defined by the rows in dmsGraphicBitmapTable that 
share a common dmsGraphicIndex, as defined above. A bitmap image denotes the 
color of each pixel within a rectangular region. The size of the rectangular 
region is defined by the dmsGraphicHeightV4 and dmsGraphicWidth objects. 

If dmsGraphicType is a value of 'monochrome1bit', each bit within the bitmap 
data corresponds to a pixel on the DMS display. Starting with the first byte 
of the bitmap data, the most significant bit defines the state of the pixel 
in the upper left corner of the rectangular region. Byte 1 through byte N of 
the bitmap data corresponds to the rectangular region by rows, left to right, 
then top to bottom. If the rectangular region is not divisible by 8, the 
remaining bits shall be 0 and contained in the lower bits of the last byte of 
the bitmap data. In this case, the total size of the bitmap image in bytes is 
given by this formula:
  B = ((dmsGraphicWidth * dmsGraphicHeightV4) + 7)/8
The first term computes the approximate size of the bitmap in bytes, +/- one 
byte. The second term computes whether the size of the bitmap in bits is 
divisible by 8; if not, an extra byte is required to hold the remaining few 
bits.

If the dmsColorScheme is monochrome8bit, colorClassic, or color24bit, and the 
graphic is defined with dmsGraphicType monochrome1bit, then pixels are 
displayed with the foreground color (bit = 1) or black (bit = 0).  Note that 
if dmsGraphicTransparentEnabled is set to 1 and dmsGraphicTransparentColor is 
set to 0 then a monochrome1bit graphic can be displayed in the same manner as 
a font character.

If dmsGraphicType is a value of 'monochrome8bit', each byte within the bitmap 
data corresponds to a pixel on the DMS display. The first byte of the bitmap 
data defines the state of the pixel in the upper left corner of the 
rectangular region. Byte 1 through byte N of the bitmap data correspond to 
the rectangular region by rows, left to right, then top to bottom. Each byte 
is one of 255 shades of the monochrome color. In this case, the formula for 
the total size of the bitmap in bytes is given by this formula:
  B = (dmsGraphicWidth*dmsGraphicHeightV4)

If dmsGraphicType is a value of 'colorClassic', each byte within the bitmap 
data corresponds to a pixel on the DMS display. The first byte of the bitmap 
data defines the state of the pixel in the upper left corner of the 
rectangular region. Byte 1 through byte N of the bitmap data correspond to 
the rectangular region by rows, left to right, then top to bottom. The data 
in each byte shall be one of the values indicated by dmsColorScheme under the 
colorClassic type. In this case, the formula for the total size of the bitmap 
in bytes is given by this formula:
  B = (dmsGraphicWidth*dmsGraphicHeightV4)

If dmsGraphicType is a value of 'color24bit, sets of three bytes within the 
bitmap data correspond to a pixel on the DMS display. The first three bytes 
of the bitmap data define the state of the pixel in the upper left corner of 
the rectangular region. Byte 1 through byte N of the bitmap data corresponds 
to the rectangular region by rows, left to right, then top to bottom. The 
first byte of the bitmap data shall be the value of blue for the upper left 
pixel. The second byte of the bitmap data shall be the value of green for the 
upper left pixel. The third byte of the bitmap data shall be the value of red 
for the upper left pixel. In this case, the formula for the total size of the 
bitmap in bytes is given by this formula:
  B = (dmsGraphicWidth*dmsGraphicHeightV4)*3

All rows of the bitmap data Table must always logically exist (that is, under 
no circumstances shall a controller produce a SuchInstance value when asked 
for a row of the dmsGraphicBitmapTable where 
dmsGraphicIndex<=dmsGraphicsMaxEntries and 
dmsGraphicBlockNumber<=dmsGraphicMaxSize/dmsGraphicBlockSize). If a GET 
request is received for a block for which no corresponding SET request has 
been accepted, then the controller shall return a block of length 
dmsGraphicBlockSize, each octet of which has the value 0 (zero). Similarly, 
when displaying a bitmap, the contents of any block within the bitmap image 
that has not been defined by a SET operation shall be assumed to be a 
sequence of octets with the value 0 (zero) and length dmsGraphicBlockSize.
--Data Examples
-- 'monochrome1bit' Example 1
--
--  Example 1 shows a graphic of an arrow as it would be shown on the 
--  DMS display. 
--  Since the graphic size is 24x7 pixels (which is divisible by 8), 
--  the bitwise layout below represents how it appears on the display.
--
--               765432107654321076543210
--             
--  BYTE1..3    000000000000110000000000
--  BYTE4..6    000000000000011100000000
--  BYTE7..9    000000000000000111100000
--  BYTE10..12  001111111111111111111000
--  BYTE13..15  000000000000000111100000
--  BYTE16..18  000000000000011100000000
--  BYTE19..21  000000000000110000000000
--
--  The following represents the byte stream of the graphic above. The
--  24 by 7 pixel graphic takes 21 bytes to define. 
--  00 0C 00 00 07 00 00 01 E0 3F FF F8 00 01 E0 00 07 00 00 0C 00
--
--
-- 'monochrome1bit' Example 2
--   The following pattern is what would be displayed. The graphic is 
--   10 pixels wide by 6 pixels high. The general appearance of the
--   sample graphic is an X followed by a 1.
--             
--  1000010010  
--  0100100110
--  0011000010
--  0011000010
--  0100100010
--  1000010111
--
--  Byte stream of example 2
--
--   Example 2 graphic is 8 bytes in length. Only 60 of the 64 bits
--   make up the graphic. The last 4 bits are buffer
--             7654321076543210
--  
--  BYTE1..2  1000010010010010
--  BYTE3..4  0110001100001000
--  BYTE5..6  1100001001001000
--  BYTE7..8  1010000101110000
--
--  The following represents the byte stream of the graphic above. The
--  10 by 6 pixel graphic takes 8 bytes to define. 
--  84 92 63 08 C2 48 A1 70
--
--
--  'color24bit' Example
--
--   Using the same graphic of an multi-colored arrow as the first example, 
--   below is how it would
--   appear on the display. A legend is listed below for color reference.
--
--  0-black, R-red, W-white, B-blue, G-green, P-purple
--
--  0000RW00000000
--  00000RRW000000
--  0000000RRRW000
--  GGGGGGGPPPPPW0
--  0000000PPPB000
--  00000PPB000000
--  0000PB00000000
--
--  The following represents the byte stream of the graphic above. The
--  14 by 7 pixel graphic takes 294 bytes to define. The bytes below
--  are and red, green, blue representation of the pixels to be displayed.
--  In hexadecimal each grouping below represents a pixel. 
--    BBGGRR where BB represents a byte of blue in hexadecimal
--       and GG represents a byte of green in hexadecimal
--       and RR represents a byte of red in hexadecimal
--
-- 000000 000000 000000 000000 0000FF FFFFFF 000000 000000 000000 000000
-- 000000 000000 000000 000000 000000 000000 000000 000000 000000 0000FF
-- 0000FF FFFFFF 000000 000000 000000 000000 000000 000000 000000 000000
-- 000000 000000 000000 000000 000000 0000FF 0000FF 0000FF FFFFFF 000000
-- 000000 000000 00FF00 00FF00 00FF00 00FF00 00FF00 00FF00 00FF00 FF33CC
-- FF33CC FF33CC FF33CC FF33CC FFFFFF 000000 000000 000000 000000 000000
-- 000000 000000 000000 FF33CC FF33CC FF33CC FF0000 000000 000000 000000
-- 000000 000000 000000 000000 000000 FF33CC FF33CC FF0000 000000 000000
-- 000000 000000 000000 000000 000000 000000 000000 000000 FF33CC FF0000
-- 000000 000000 000000 000000 000000 000000 000000 000000

<Table Type> static
<Object Identifier> 1.3.6.1.4.1.1206.4.2.3.10.7"
::= {graphicDefinition 7}

dmsGraphicBitmapEntry OBJECT-TYPE
SYNTAX      DmsGraphicBitmapEntry
MAX-ACCESS  not-accessible
STATUS      current 
DESCRIPTION "<Definition> Parameters of the Graphic Bitmap Table."
INDEX {dmsGraphicBitmapIndex, dmsGraphicBlockNumber}
::= {dmsGraphicBitmapTable 1}

DmsGraphicBitmapEntry::= SEQUENCE {
	dmsGraphicBitmapIndex	Integer32,
	dmsGraphicBlockNumber	Integer32,
	dmsGraphicBlockBitmap	OCTET STRING} 

-- 5.12.7.1	Graphic Index Parameter 
dmsGraphicBitmapIndex  OBJECT-TYPE 
SYNTAX      Integer32 (1..255) 
MAX-ACCESS  read-only 
STATUS      current  
DESCRIPTION  
"<Definition> Indicates the row number of the entry. This index directly 
corresponds to dmsGraphicIndex, the index of dmsGraphicTable.
<Parameter Type> Status
<Object Identifier> 1.3.6.1.4.1.1206.4.2.3.10.7.1"
::= { dmsGraphicBitmapEntry 1 }

-- 5.12.7.2	Graphic Block Number Parameter 
dmsGraphicBlockNumber  OBJECT-TYPE 
SYNTAX      Integer32 (1..255) 
MAX-ACCESS  read-only 
STATUS      current  
DESCRIPTION  
"<Definition> Indicates the offset of the corresponding 
dmsGraphicBlockBitmap's data within the graphic image, in 
dmsGraphicBlockSize-sized chunks.
<Parameter Type> Status
<Object Identifier> 1.3.6.1.4.1.1206.4.2.3.10.7.2"
::= { dmsGraphicBitmapEntry 2 }

-- 5.12.7.3	Graphic Block Bitmap Parameter 
dmsGraphicBlockBitmap  OBJECT-TYPE 
SYNTAX      OCTET STRING 
MAX-ACCESS  read-write 
STATUS      current  
DESCRIPTION  
"<Definition> The contents of the given block of the bitmap of the graphic 
image. Each dmsGraphicBlockBitmap value is a sequence of dmsGraphicBlockSize 
octets. If a SET request for dmsGraphicBlockBitmap contains less than 
dmsGraphicBlockSize octets, then the supplied data shall be loaded into the 
beginning of the block, and the remainder of the block shall be filled with 
octets with the value 0 (zero). If a SET request for dmsGraphicBlockBitmap 
contains more than dmsGraphicBlockSize octets, the device shall return a SNMP 
wrongValue error. If a GET request is received for a dmsGraphicBlockBitmap 
entry for which no SET request has been accepted, then the controller shall 
respond with a successful GET reply, and the value returned to the central 
system shall be an OCTET STRING of dmsGraphicBlockSize octets, all of which 
have the value 0 (zero).
<Parameter Type> Configuration
<Object Identifier> 1.3.6.1.4.1.1206.4.2.3.10.7.3"
::= { dmsGraphicBitmapEntry 3 }

-- 5.12.8	Available Graphic Memory Version 4 Parameter
dmsAvailableGraphicMemoryV4  OBJECT-TYPE 
SYNTAX      Unsigned32
UNITS       "octets" 
MAX-ACCESS  read-only 
STATUS      current  
DESCRIPTION  
"<Definition> An indication of the amount of memory left, in octets (i.e., 
eight-bit bytes), to store graphics.
<Parameter Type> Status
<Object Identifier> 1.3.6.1.4.1.1206.4.2.3.10.8"
::= { graphicDefinition 8 }

-- 5.12.9	Maximum Graphic Size Parameter 
dmsGraphicMaxSizeV4  OBJECT-TYPE 
SYNTAX      Unsigned32 (0..4294967295)
UNITS       "octets" 
MAX-ACCESS  read-only 
STATUS      current  
DESCRIPTION  
"<Definition> Indicates the maximum size (in bytes) of each graphic the sign 
is capable of storing. This value shall be an even multiple of the object 
dmsGraphicBlockSize.
<Parameter Type> Status
<Object Identifier> 1.3.6.1.4.1.1206.4.2.3.10.9"
::= { graphicDefinition 9 }

-- 5.12.10	Graphic File Error Description Parameter 
dmsGraphicFileErrorDescr  OBJECT-TYPE 
SYNTAX      SnmpAdminString
MAX-ACCESS  read-only 
STATUS      current  
DESCRIPTION  
"<Definition> Indicates the result of the last attempt to parse a graphic 
file into the various fields after a set to an instance of 
dmsGraphicFilename.
<Parameter Type> Status
<Object Identifier> 1.3.6.1.4.1.1206.4.2.3.10.10"
::= { graphicDefinition 10 }

-- 5.12.11	Graphic Error Description Parameter 
dmsGraphicErrorDescr  OBJECT-TYPE 
SYNTAX      SnmpAdminString
MAX-ACCESS  read-only 
STATUS      current  
DESCRIPTION  
"<Definition> Indicates the result of the last attempt to set an instance of 
dmsGraphicStatus to 'readyForUseReq'.
<Parameter Type> Status
<Object Identifier> 1.3.6.1.4.1.1206.4.2.3.10.11"
::= { graphicDefinition 11 }

-- 5.12.12	Graphic Path Parameter 
dmsGraphicPath  OBJECT-TYPE 
SYNTAX      SnmpAdminString
MAX-ACCESS  read-only 
STATUS      current  
DESCRIPTION  
" <Definition> Indicates the absolute path for storing graphic files, 
including the trailing slash. The path may use symbolic links (symlinks). 
<Informative> It is recommended that the graphic path 1) should only be used 
for storing user-defined graphic files, 2) should not reveal sensitive 
directory structures, and 3) should be presented in Unix directory format. 
For example, due to the use of off-the-shelf software, there might be 
advantages to storing the graphics in '/application/uploads/graphics'. 
However, to avoid revealing the presence of the 'application' directory, 
which may contain sensitive files, a symlink could be created to equate the 
'user' directory with '/application/uploads/'; the value of this object would 
then be '/user/graphics'.
<Parameter Type> Status
<Object Identifier> 1.3.6.1.4.1.1206.4.2.3.10.12"
::= { graphicDefinition 12 }

-- 5.13	Callable Commands
dmsCallable  OBJECT-IDENTITY 
STATUS  current
DESCRIPTION
"<Definition> This node is an identifier used to group all objects for 
commands that can be called in the DMS. 
<Object Identifier> 1.3.6.1.4.1.1206.4.2.3.11"
::= { dms 11 }

-- 5.13.1	Number of Callable Messages 
dmsNumCallableMessages  OBJECT-TYPE 
SYNTAX      Integer32 (0..255)
UNITS       "entries" 
MAX-ACCESS  read-only 
STATUS      current  
DESCRIPTION  
"<Definition> Indicates the number of rows currently stored in the 
dmsCallableMessagesTable. The messages are not required to be sequential.
<Parameter Type> Status
<Object Identifier> 1.3.6.1.4.1.1206.4.2.3.11.1"
::= { dmsCallable 1 }

-- 5.13.2	Callable Command Table 
dmsCallableMessageTable  OBJECT-TYPE 
SYNTAX      SEQUENCE OF DmsCallableMessageEntry
MAX-ACCESS  not-accessible
STATUS      current 
DESCRIPTION "<Definition> A table containing a list of message activation 
codes that can be called by other routines, such as the fdActionPointer (as 
defined in ISO 26048-1), which can be called by the fdCondTriggerTable. 
Implementations that support this table and the fdActionTable shall allow any 
instance of fdActionPointer to reference any row of this table.
<Informative> Whereas the dmsActionTable uses the MessageIDCode to define the 
contents of the schedule row of the message table, this table uses the 
MessageActivateCode to immediately activate a message on the sign with a 
defined duration and priority (i.e., if successful the MultiString is stored 
in dmsMessageMultiString.5.1)
<Table Type> dynamic
<Object Identifier> 1.3.6.1.4.1.1206.4.2.3.11.2"
::= { dmsCallable 2 }

dmsCallableMessageEntry  OBJECT-TYPE
SYNTAX      DmsCallableMessageEntry
MAX-ACCESS  not-accessible
STATUS      current 
DESCRIPTION "<Definition> Parameters of the dmsCallableMessageTable.
<Object Identifier> 1.3.6.1.4.1.1206.4.2.3.11.2.1"
INDEX {dmsCallableMessageIndex}
::= { dmsCallableMessageTable 1}

DmsCallableMessageEntry ::= SEQUENCE {
   dmsCallableMessageIndex        Integer32,
   dmsCallableMessageCode         MessageActivationCodeV4, 
   dmsCallableMessageStorageType  StorageType,
   dmsCallableMessageRowStatus    RowStatus } 

-- 5.13.2.1	Callable Message Index Parameter 
dmsCallableMessageIndex  OBJECT-TYPE 
SYNTAX      Integer32 (1..255) 
MAX-ACCESS  not-accessible 
STATUS      current  
DESCRIPTION  
"<Definition> Index of the row entry within the CallableMessageTable.
<Parameter Type> Status
<Object Identifier> 1.3.6.1.4.1.1206.4.2.3.11.2.1.1"
::= { dmsCallableMessageEntry 1 }

-- 5.13.2.2	Callable Message Activation Code Parameter 
dmsCallableMessageCode  OBJECT-TYPE 
SYNTAX      MessageActivationCodeV4 
MAX-ACCESS  read-create 
STATUS      current  
DESCRIPTION  
"<Definition> The message activation code to be called when this row is 
called by an outside source, such as the fdActionPointer.
<Parameter Type> Configuration
<Object Identifier> 1.3.6.1.4.1.1206.4.2.3.11.2.1.2"
::= { dmsCallableMessageEntry 2 }

-- 5.13.2.3	Callable Message Storage Type Parameter 
dmsCallableMessageStorageType  OBJECT-TYPE 
SYNTAX      StorageType 
MAX-ACCESS  read-create 
STATUS      current  
DESCRIPTION  
"<Definition> This object defines whether this callable message is kept in 
volatile storage and lost upon reboot or if this row survives a reboot by 
being stored in non-volatile or permanent storage. Rows having the value 
'permanent' shall allow write access to its associated 
fdCallableCommandRowStatus to disable the callable command.
<Parameter Type> Configuration
<Object Identifier> 1.3.6.1.4.1.1206.4.2.3.11.2.1.3"
::= { dmsCallableMessageEntry 3 }

-- 5.13.2.4	Callable Message Row Status Parameter 
dmsCallableMessageRowStatus  OBJECT-TYPE 
SYNTAX      RowStatus 
MAX-ACCESS  read-create 
STATUS      current  
DESCRIPTION  
"<Definition> The object that indicates the status of this callable message 
and allows entries to be added and removed from this table. All other read-
create objects in this entry can only be modified when the value of this 
object is not 'active'. Implementations shall support both createAndGo and 
createAndWait.
<Parameter Type> Configuration
<Object Identifier> 1.3.6.1.4.1.1206.4.2.3.11.2.1.4"
::= { dmsCallableMessageEntry 4 }

-- 5.13.3	Sign Display Shutdown
dmsCallableSignDisplayShutdown OBJECT-IDENTITY 
STATUS current
DESCRIPTION
"<Definition> This object can be called by the fdActionTable to force the 
sign display to shutdown. This can be useful to prevent damage to components 
(e.g., due to overheating).
<Object Identifier> 1.3.6.1.4.1.1206.4.2.3.11.3"
::= { dmsCallable 3 }

-- 5.13.4	Sign Display Restart
dmsCallableSignDisplayRestart OBJECT-IDENTITY 
STATUS current
DESCRIPTION
"<Definition> This object can be called by the fdActionTable to force the 
sign display to restart after a shutdown.
<Object Identifier> 1.3.6.1.4.1.1206.4.2.3.11.4"
::= { dmsCallable 4 }

-- 5.14	Object Groups
dmsConformance OBJECT-IDENTITY 
STATUS current
DESCRIPTION
"<Definition> This node is an identifier used to manage the conformance for 
DMS. 
<Object Identifier> 1.3.6.1.4.1.1206.4.2.3.127"
::= { dms 127 }

dmsCompliances OBJECT-IDENTITY 
STATUS       current 
DESCRIPTION 
"<Definition> A node for compliance statements for DMS objects. 
<Object Identifier> 1.3.6.1.4.1.1206.4.2.3.127.1" 
::= {dmsConformance 1}

dmsGroups OBJECT-IDENTITY
STATUS     current
DESCRIPTION
"<Definition> A node for group definitions related to the DMS MIB.
<Object Identifier> 1.3.6.1.4.1.1206.4.2.3.127.2"
::= { dmsConformance 2 }

-- 5.14.1	DMS Core Group
dmsCoreGroupV4 OBJECT-GROUP
OBJECTS { dmsSignType,
          dmsSignTechnology,
          dmsMessageMemoryType,
          dmsMessageNumber,
          dmsMessageMultiString,
          dmsMessageOwner,
          dmsMessageBeacon,
          dmsMessagePixelService,
          dmsMessageRunTimePriority,
          dmsMessageStatus,
          dmsControlMode,
          dmsActivateMsgError,
          dmsMultiSyntaxError,
          dmsMultiSyntaxErrorPosition,
          dmsMultiOtherErrorDescription,
          dmsActivateMessageV4,
          dmsActivateErrorMsgCodeV4,
          dmsMessageTimeRemaining,
          shortErrorStatus,
          dmsOtherShortErrorDescr }
STATUS  current
DESCRIPTION
"<Definition> The core set of DMS objects required for all implementations.
<Object Identifier> 1.3.6.1.4.1.1206.4.2.3.127.2.1"
::= { dmsGroups 1 }

-- 5.14.2	VMS Core Group
vmsCoreGroupV4 OBJECT-GROUP
OBJECTS { monochromeColor,
          defaultFlashOn,
          defaultFlashOnActivate,
          defaultFlashOff,
          defaultFlashOffActivate,
          defaultFont,
          defaultFontActivate,
          defaultJustificationLine,
          defaultJustificationLineActivate,
          defaultJustificationPage,
          defaultJustificationPageActivate,
          defaultPageOnTime,
          defaultPageOnTimeActivate,
          defaultPageOffTime,
          defaultPageOffTimeActivate,
          defaultBackgroundRGB,
          defaultBackgroundRGBActivate,
          defaultForegroundRGB,
          defaultForegroundRGBActivate,
          defaultCharacterSet,
          dmsColorScheme,
          dmsSupportedMultiTagsV4,
          dmsMaxNumberPages,
          dmsMaxMultiStringLength,
          dmsNumPermanentMsg,
          dmsNumChangeableMsg,
          dmsMaxChangeableMsg,
          dmsFreeChangeableMemory,
          dmsNumVolatileMsg,
          dmsMaxVolatileMsg,
          dmsFreeVolatileMemory,
          dmsMessageCRC,
          dmsValidateMessageError,
          dmsMemoryMgmt }
STATUS  current
DESCRIPTION
"<Definition> The core set of VMS objects required for all variable message 
sign implementations.
<Object Identifier> 1.3.6.1.4.1.1206.4.2.3.127.2.2"
::= { dmsGroups 2 }

-- 5.14.3	Matrix Group
dmsMatrixGroupV4 OBJECT-GROUP
OBJECTS { vmsCharacterHeightPixels,
          vmsCharacterWidthPixels,
          vmsSignHeightPixels,
          vmsSignWidthPixels,
          vmsHorizontalPitch,
          vmsVerticalPitch,
          pixelFailureTableNumRows,
          pixelFailureDetectionType,
          pixelFailureIndex,
          pixelFailureXLocation,
          pixelFailureYLocation,
          pixelFailureStatus,
          pixelTestActivation,
          dmsPixelStatusIndex,
          dmsPixelStatusV4,
          dmsPixelFailureTestRows,
          dmsPixelFailureMessageRows }
STATUS  current
DESCRIPTION
"<Definition> The set of DMS objects required for all matrix signs.
<Object Identifier> 1.3.6.1.4.1.1206.4.2.3.127.2.3"
::= { dmsGroups 3 }

-- 5.14.4	Beacon Group
dmsBeaconGroupV4 OBJECT-GROUP
OBJECTS { dmsBeaconCount,
          dmsBeaconMaxPlans,
          dmsBeaconXLocation,
          dmsBeaconYLocation,
          dmsBeaconWidth,
          dmsBeaconHeight,
          dmsBeaconColorScheme,
          dmsBeaconFlashResolution,
          dmsBeaconPlanDescr,
          dmsBeaconPlanCycle,
          dmsBeaconPlanStorageType,
          dmsBeaconPlanRowStatus,
          dmsBeaconPlanDetailCycle,
          dmsBeaconPlanDetailOffset,
          dmsBeaconPlanDetailFlash,
          dmsBeaconPlanDetailColor }
STATUS  current
DESCRIPTION
"<Definition> The set of DMS objects required to manage the DMS beacons.
<Object Identifier> 1.3.6.1.4.1.1206.4.2.3.127.2.4"
::= { dmsGroups 4 }

-- 5.14.5	Display Capabilities Group
dmsDisplayCapabilitiesGroupV4 OBJECT-GROUP
OBJECTS { dmsSignAccess,
          dmsSignHeight,
          dmsSignWidth,
          dmsHorizontalBorder,
          dmsVerticalBorder,
          dmsLegend }
STATUS  current
DESCRIPTION
"<Definition> The set of DMS objects required to determine the display 
capabilities.
<Object Identifier> 1.3.6.1.4.1.1206.4.2.3.127.2.5"
::= { dmsGroups 5 }

-- 5.14.6	Display Location Group
dmsDisplayLocationGroupV4 OBJECT-GROUP
OBJECTS { dmsDisplayLatitude,
          dmsDisplayLongitude,
          dmsDisplayDirection,
          dmsDisplayOffsetLatitude,
          dmsDisplayOffsetLongitude }
STATUS  current
DESCRIPTION
"<Definition> The set of DMS objects required to identify the location of the 
display.
<Object Identifier> 1.3.6.1.4.1.1206.4.2.3.127.2.6"
::= { dmsGroups 6 }

-- 5.14.7	Current Message Group
dmsCurrentMessageGroupV4 OBJECT-GROUP
OBJECTS { dmsMsgTableSource,
          dmsMsgSourceMode,
          dmsMsgRequesterAddressType,
          dmsMsgRequesterAddress,
          dmsMsgRequesterSecurityName }
STATUS  current
DESCRIPTION
"<Definition> The set of DMS objects required to monitor the current message.
<Object Identifier> 1.3.6.1.4.1.1206.4.2.3.127.2.7"
::= { dmsGroups 7 }

-- 5.14.8	DMS Font Group
dmsFontGroupV4 OBJECT-GROUP
OBJECTS { numFonts,
          fontIndex,
          fontNumber,
          fontName,
          fontHeight,
          fontCharSpacing,
          fontLineSpacing,
          fontVersionID,
          fontStatus,
          maxFontCharacters,
          characterNumber,
          characterWidth,
          characterBitmap,
          fontMaxCharacterSize }
STATUS  current
DESCRIPTION
"<Definition> The set of DMS objects required to support fonts.
<Object Identifier> 1.3.6.1.4.1.1206.4.2.3.127.2.8"
::= { dmsGroups 8 }

-- 5.14.9	DMS Graphics Group
dmsGraphicsGroupV4 OBJECT-GROUP
OBJECTS { dmsGraphicMaxEntries,
          dmsGraphicNumEntries,
          dmsGraphicMaxSizeV4,
          dmsGraphicBlockSize,
          dmsGraphicIndex,
          dmsGraphicNumber,
          dmsGraphicName,
          dmsGraphicWidth,
          dmsGraphicType,
          dmsGraphicID,
          dmsGraphicTransparentEnabled,
          dmsGraphicTransparentColor,
          dmsGraphicStatus,
          dmsGraphicHeightV4,
          dmsGraphicFilename,
          dmsGraphicBitmapIndex,
          dmsGraphicBlockNumber,
          dmsGraphicBlockBitmap,
          dmsAvailableGraphicMemoryV4,
          dmsGraphicFileErrorDescr,
          dmsGraphicErrorDescr,
          dmsGraphicPath }
STATUS  current
DESCRIPTION
"<Definition> The set of DMS objects required to support graphics.
<Object Identifier> 1.3.6.1.4.1.1206.4.2.3.127.2.9"
::= { dmsGroups 9 }

-- 5.14.10	Drum Group
dmsDrumGroupV4 OBJECT-GROUP
OBJECTS { dmsActivateMessageState }
STATUS  current
DESCRIPTION
"<Definition> The set of DMS objects required to manage drum signs.
<Object Identifier> 1.3.6.1.4.1.1206.4.2.3.127.2.10"
::= { dmsGroups 10 }

-- 5.14.11	Pixel Service Group
dmsPixelServiceGroupV4 OBJECT-GROUP
OBJECTS { vmsPixelServiceFrequency,
          vmsPixelServiceTime,
          vmsPixelServiceDurationV4 }
STATUS  current
DESCRIPTION
"<Definition> The set of DMS objects required to manage pixel service.
<Object Identifier> 1.3.6.1.4.1.1206.4.2.3.127.2.11"
::= { dmsGroups 11 }

-- 5.14.12	Illumination Group
dmsIlluminationGroupV4 OBJECT-GROUP
OBJECTS { dmsIllumControl,
          dmsIllumNumBrightLevels,
          dmsIllumBrightLevelStatus,
          dmsIllumManLevel,
          dmsIllumLightOutputStatus }
STATUS  current
DESCRIPTION
"<Definition> The set of DMS objects required to manually control 
illumination.
<Object Identifier> 1.3.6.1.4.1.1206.4.2.3.127.2.12"
::= { dmsGroups 12 }

-- 5.14.13	Automatic Brightness Group
dmsAutoBrightGroupV4 OBJECT-GROUP
OBJECTS { dmsIllumBrightnessValues,
          dmsIllumBrightnessValuesError }
STATUS  current
DESCRIPTION
"<Definition> The set of DMS objects required to manage automatic brightness 
of the sign display.
<Object Identifier> 1.3.6.1.4.1.1206.4.2.3.127.2.13"
::= { dmsGroups 13 }

-- 5.14.14	DMS Schedule Group
dmsScheduleGroupV4 OBJECT-GROUP
OBJECTS { numActionTableEntries,
          dmsActionIndex,
          dmsActionMsgCode }
STATUS  current
DESCRIPTION
"<Definition> The set of DMS objects required to implement scheduled messages 
(i.e., row 6 of the message table).
<Object Identifier> 1.3.6.1.4.1.1206.4.2.3.127.2.14"
::= { dmsGroups 14 }

-- 5.14.15	Callable Message Group
dmsCallableMessageGroupV4 OBJECT-GROUP
OBJECTS { dmsNumCallableMessages,
          dmsCallableMessageCode,
          dmsCallableMessageStorageType,
          dmsCallableMessageRowStatus }
STATUS  current
DESCRIPTION
"<Definition> The set of DMS objects required to implement messages based on 
internal configurable logic (e.g., ISO 26048-1 conditional triggers).
<Object Identifier> 1.3.6.1.4.1.1206.4.2.3.127.2.15"
::= { dmsGroups 15 }

-- 5.14.16	SRSA Pixel Group
dmsSrsaPixelGroupV4 OBJECT-GROUP
OBJECTS { dmsSrsaPixelsTop,
          dmsSrsaPixelsLeft,
          dmsSrsaPixelsBottom,
          dmsSrsaPixelsRight }
STATUS  current
DESCRIPTION
"<Definition> The set of DMS objects required to determine the pixels 
associated with an SRSA entry (see ISO 26048-1).
<Object Identifier> 1.3.6.1.4.1.1206.4.2.3.127.2.16"
::= { dmsGroups 16 }

-- 5.14.17	MULTI Fields Group
dmsMultiFieldsGroupV4 OBJECT-GROUP
OBJECTS { statMultiFieldIndex,
          statMultiFieldRows,
          statMultiFieldCode,
          statMultiCurrentFieldValue }
STATUS  current
DESCRIPTION
"<Definition> The set of DMS objects required to monitor MULTI field values.
<Object Identifier> 1.3.6.1.4.1.1206.4.2.3.127.2.17"
::= { dmsGroups 17 }

-- 5.14.18	Speed Limit Group
dmsSpeedLimitGroupV4 OBJECT-GROUP
OBJECTS { dmsCurrentSpeedLimit }
STATUS  current
DESCRIPTION
"<Definition> The set of DMS objects required to manage the speed limit to be 
associated with the sign.
<Object Identifier> 1.3.6.1.4.1.1206.4.2.3.127.2.18"
::= { dmsGroups 18 }

-- 5.14.19	Short Power Recovery Group
dmsShortPowerRecoveryGroupV4 OBJECT-GROUP
OBJECTS { dmsShortPowerRecoveryMessage }
STATUS  current
DESCRIPTION
"<Definition> The set of DMS objects required to manage the message to be 
displayed after a short power recovery.
<Object Identifier> 1.3.6.1.4.1.1206.4.2.3.127.2.19"
::= { dmsGroups 19 }

-- 5.14.20	Long Power Recovery Group
dmsLongPowerRecoveryGroupV4 OBJECT-GROUP
OBJECTS { dmsShortPowerLossTime,
          dmsLongPowerRecoveryMessage }
STATUS  current
DESCRIPTION
"<Definition> The set of DMS objects required to manage the message to be 
displayed after a long power recovery.
<Object Identifier> 1.3.6.1.4.1.1206.4.2.3.127.2.20"
::= { dmsGroups 20 }

-- 5.14.21	Power Loss Group
dmsPowerLossGroupV4 OBJECT-GROUP
OBJECTS { dmsPowerLossMessage }
STATUS  current
DESCRIPTION
"<Definition> The set of DMS objects required to manage the message to be 
displayed during a power loss.
<Object Identifier> 1.3.6.1.4.1.1206.4.2.3.127.2.21"
::= { dmsGroups 21 }

-- 5.14.22	Reset Message Group
dmsResetMessageGroupV4 OBJECT-GROUP
OBJECTS { dmsResetMessage }
STATUS  current
DESCRIPTION
"<Definition> The set of DMS objects required to manage the message to be 
displayed after a reset.
<Object Identifier> 1.3.6.1.4.1.1206.4.2.3.127.2.22"
::= { dmsGroups 22 }

-- 5.14.23	Communicaions Loss Group
dmsCommLossGroupV4 OBJECT-GROUP
OBJECTS { dmsCommunicationsLossMessage,
          dmsTimeCommLoss }
STATUS  current
DESCRIPTION
"<Definition> The set of DMS objects required to manage the message to be 
displayed during a prolonged period without receiving any communications.
<Object Identifier> 1.3.6.1.4.1.1206.4.2.3.127.2.23"
::= { dmsGroups 23 }

-- 5.14.24	End Duration Group
dmsEndDurationGroupV4 OBJECT-GROUP
OBJECTS { dmsEndDurationMessage }
STATUS  current
DESCRIPTION
"<Definition> The set of DMS objects required to manage the message to be 
displayed at the end of the previously displayed message's duration.
<Object Identifier> 1.3.6.1.4.1.1206.4.2.3.127.2.24"
::= { dmsGroups 24 }

END
